'==============================================================================
' NAME:         Parametric Product Configurator Template
' AUTHOR:       Jugoslav Ilic
' DATE:         04.09.2026.
' VERSION:      1.0.0
' LICENSE:      MIT — free to use with attribution
' GITHUB:       github.com/iddj27510/iLogic-Library
'
' DESCRIPTION:
'   Reusable template for parametric product configurators.
'   Form with input fields, validation, auto-generated Description.
'
' PARAMETERS:
'   None — configured at the top of the script.
'
' ASSUMPTIONS:
'   Active document must be a Part or Assembly document.
'
' TESTED ON:
'   Autodesk Inventor 2027
'
' NOTES:
'   This is a template — the user must adapt parameter names
'   and validation rules for their specific product.
'==============================================================================

' ============================================================
' CONFIGURATION — edit before use
' ============================================================
Dim aParams As New List(Of String) From {"Length", "Width", "Height", "Material"}
Dim aMaterials As New List(Of String) From {"S235", "S355", "SS304", "AL5052"}
Dim nMinLength As Double = 100
Dim nMaxLength As Double = 1000
Dim nMinWidth As Double = 100
Dim nMaxWidth As Double = 500
Dim nMinHeight As Double = 50
Dim nMaxHeight As Double = 300
' ============================================================

' --- Context check ---
Dim oDoc As Document = ThisApplication.ActiveDocument
If oDoc Is Nothing Then
    MsgBox("No active document.", vbExclamation, "Error")
    Exit Sub
End If

If Not (TypeOf oDoc Is PartDocument Or TypeOf oDoc Is AssemblyDocument) Then
    MsgBox("Run this rule from a Part or Assembly document.", vbExclamation, "Wrong Document Type")
    Exit Sub
End If

' --- Get current parameters ---
Dim oParams As Parameters = oDoc.ComponentDefinition.Parameters

Dim dLength As Double = 500
Dim dWidth As Double = 300
Dim dHeight As Double = 150
Dim sMaterial As String = "S235"

Try
    dLength = oParams.Item("Length").Value
Catch
End Try

Try
    dWidth = oParams.Item("Width").Value
Catch
End Try

Try
    dHeight = oParams.Item("Height").Value
Catch
End Try

' --- User input form ---
Dim sMsg As String = "=== Parametric Configurator ===" & vbCrLf & vbCrLf
sMsg &= "Length (mm): " & dLength & vbCrLf
sMsg &= "Width (mm): " & dWidth & vbCrLf
sMsg &= "Height (mm): " & dHeight & vbCrLf
sMsg &= "Material: " & sMaterial & vbCrLf & vbCrLf
sMsg &= "Do you want to configure?"

If MsgBox(sMsg, vbYesNo + vbQuestion, "Parametric Configurator") <> vbYes Then
    Exit Sub
End If

' --- Get new values ---
Dim sLength As String = InputBox("Length (mm):", "Parametric Configurator", dLength)
Dim sWidth As String = InputBox("Width (mm):", "Parametric Configurator", dWidth)
Dim sHeight As String = InputBox("Height (mm):", "Parametric Configurator", dHeight)

' --- Validate ---
If sLength = "" Or sWidth = "" Or sHeight = "" Then
    MsgBox("Configuration cancelled.", vbInformation, "Cancelled")
    Exit Sub
End If

Dim dNewLength As Double = Val(sLength)
Dim dNewWidth As Double = Val(sWidth)
Dim dNewHeight As Double = Val(sHeight)

If dNewLength < nMinLength Or dNewLength > nMaxLength Then
    MsgBox("Length must be between " & nMinLength & " and " & nMaxLength & " mm.", vbExclamation, "Validation Error")
    Exit Sub
End If

If dNewWidth < nMinWidth Or dNewWidth > nMaxWidth Then
    MsgBox("Width must be between " & nMinWidth & " and " & nMaxWidth & " mm.", vbExclamation, "Validation Error")
    Exit Sub
End If

If dNewHeight < nMinHeight Or dNewHeight > nMaxHeight Then
    MsgBox("Height must be between " & nMinHeight & " and " & nMaxHeight & " mm.", vbExclamation, "Validation Error")
    Exit Sub
End If

' --- Apply changes ---
Try
    oParams.Item("Length").Value = dNewLength
    oParams.Item("Width").Value = dNewWidth
    oParams.Item("Height").Value = dNewHeight

    ThisApplication.ActiveDocument.Update()

    ' --- Auto-generate Description ---
    Dim oProps As PropertySet = oDoc.PropertySets.Item("Design Tracking Properties")
    Dim sDescription As String = sMaterial & " " & dNewLength & "x" & dNewWidth & "x" & dNewHeight

    Try
        oProps.Item("Description").Value = sDescription
    Catch
        oDoc.PropertySets.Item("Design Tracking Properties").Add(sDescription, "Description")
    End Try

    oDoc.Save()

    MsgBox("Configuration completed!" & vbCrLf & vbCrLf & _
           "Length: " & dNewLength & " mm" & vbCrLf & _
           "Width: " & dNewWidth & " mm" & vbCrLf & _
           "Height: " & dNewHeight & " mm" & vbCrLf & _
           "Description: " & sDescription, vbInformation, "Parametric Configurator")

Catch ex As Exception
    MsgBox("Error applying configuration: " & ex.Message, vbExclamation, "Error")
End Try
