'==============================================================================
' NAME:         Surface Coating & Finish Validator
' AUTHOR:       Jugoslav Ilic
' DATE:         04.09.2026.
' VERSION:      1.0.0
' LICENSE:      MIT — free to use with attribution
' GITHUB:       github.com/iddj27510/iLogic-Library
'
' DESCRIPTION:
'   Validates Surface Coating iProperty against an approved list.
'   Detects empty fields and invalid values.
'
' PARAMETERS:
'   None — configured at the top of the script.
'
' ASSUMPTIONS:
'   Active document must be an Assembly document.
'
' TESTED ON:
'   Autodesk Inventor 2027
'
' NOTES:
'   Approved values are configured at the top of the script.
'==============================================================================

' ============================================================
' CONFIGURATION — edit before use
' ============================================================
Dim sCoatingProperty As String = "Surface Coating"
Dim aAllowedValues As New List(Of String) From {
    "Powder Coat RAL9003",
    "Powder Coat RAL9010",
    "Galvanized",
    "Passivated",
    "Electropolished",
    "Anodized",
    "None"
}
' ============================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument

' --- Scan assembly ---
Dim errors As New List(Of String)
Dim warnings As New List(Of String)

ScanForCoating(oAsmDoc.ComponentDefinition.Occurrences, errors, warnings, 0)

' --- Generate report ---
Dim report As String = "=== Surface Coating Validator ===" & vbCrLf & vbCrLf

If errors.Count > 0 Then
    report &= "ERRORS (" & errors.Count & "):" & vbCrLf
    For Each s As String In errors
        report &= "  ! " & s & vbCrLf
    Next
Else
    report &= "No errors found." & vbCrLf
End If

If warnings.Count > 0 Then
    report &= vbCrLf & "WARNINGS (" & warnings.Count & "):" & vbCrLf
    For Each s As String In warnings
        report &= "  - " & s & vbCrLf
    Next
End If

MsgBox(report, vbInformation, "Surface Coating Validator")

'==============================================================================
' HELPER FUNCTIONS
'==============================================================================

Sub ScanForCoating(oOccs As ComponentOccurrences, errors As List(Of String), warnings As List(Of String), nLevel As Integer)
    Dim oOcc As ComponentOccurrence
    For Each oOcc In oOccs
        Try
            If oOcc.DefinitionDocumentType = DocumentTypeEnum.kVirtualComponentDocumentObject Then
                Continue For
            End If

            If oOcc.DefinitionDocumentType = DocumentTypeEnum.kAssemblyDocumentObject Then
                Dim oSubAsm As AssemblyDocument = oOcc.Definition.Document
                ScanForCoating(oSubAsm.ComponentDefinition.Occurrences, errors, warnings, nLevel + 1)
                Continue For
            End If

            If oOcc.DefinitionDocumentType = DocumentTypeEnum.kPartDocumentObject Then
                Dim oPart As PartDocument = oOcc.Definition.Document
                Dim oProps As PropertySet = oPart.PropertySets.Item("Design Tracking Properties")

                Dim sCoating As String = ""
                Try
                    sCoating = oProps.Item(sCoatingProperty).Value.ToString().Trim()
                Catch
                End Try

                If sCoating = "" Then
                    warnings.Add(oOcc.Name & " — Surface Coating is empty")
                Else
                    Dim bValid As Boolean = False
                    For Each sAllowed As String In aAllowedValues
                        If sCoating = sAllowed Then
                            bValid = True
                            Exit For
                        End If
                    Next

                    If Not bValid Then
                        errors.Add(oOcc.Name & " — Invalid Surface Coating: '" & sCoating & "'")
                    End If
                End If
            End If

        Catch ex As Exception
            errors.Add(oOcc.Name & " — " & ex.Message)
        End Try
    Next
End Sub
