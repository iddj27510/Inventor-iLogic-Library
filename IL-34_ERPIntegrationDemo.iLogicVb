'==============================================================================
' NAME:         ERP Integration Live Read Demo
' AUTHOR:       Jugoslav Ilic
' DATE:         04.09.2026.
' VERSION:      1.0.0
' LICENSE:      MIT — free to use with attribution
' GITHUB:       github.com/iddj27510/iLogic-Library
'
' DESCRIPTION:
'   Demo ERP read integration. Reads data from a CSV file (ERP simulation)
'   and populates iProperties.
'
' PARAMETERS:
'   None — configured at the top of the script.
'
' ASSUMPTIONS:
'   Active document must be a Part document.
'
' TESTED ON:
'   Autodesk Inventor 2027
'
' NOTES:
'   Wyma Solutions: Ostendo ERP read integration (read only, not write).
'   Demo uses CSV as a proxy for ERP.
'==============================================================================

' ============================================================
' CONFIGURATION — edit before use
' ============================================================
Dim sCSVPath As String = ""
' ============================================================

' --- Context check ---
Dim oDoc As Document = ThisApplication.ActiveDocument
If oDoc Is Nothing Then
    MsgBox("No active document.", vbExclamation, "Error")
    Exit Sub
End If

If Not (TypeOf oDoc Is PartDocument) Then
    MsgBox("Run this rule from a Part document.", vbExclamation, "Wrong Document Type")
    Exit Sub
End If

Dim oPartDoc As PartDocument = oDoc

' --- Get Part Number ---
Dim sPartNumber As String = ""
Try
    sPartNumber = oPartDoc.PropertySets.Item("Design Tracking Properties").Item("Part Number").Value.ToString().Trim()
Catch
    MsgBox("Part Number is empty.", vbExclamation, "Error")
    Exit Sub
End Try

' --- Find CSV file ---
If sCSVPath = "" Then
    sCSVPath = System.IO.Path.GetDirectoryName(oPartDoc.FullFileName) & "\ERP_Data.csv"
End If

If Not System.IO.File.Exists(sCSVPath) Then
    MsgBox("ERP data file not found:" & vbCrLf & sCSVPath, vbExclamation, "File Not Found")
    Exit Sub
End If

' --- Read CSV and find part ---
Dim sFound As String = ""
Try
    Dim sLines() As String = System.IO.File.ReadAllLines(sCSVPath)

    For i As Integer = 1 To sLines.Length - 1
        Dim sLine As String = sLines(i)
        Dim aFields() As String = sLine.Split(",")

        If aFields(0).Trim() = sPartNumber Then
            sFound = sLine
            Exit For
        End If
    Next
Catch ex As Exception
    MsgBox("Error reading CSV: " & ex.Message, vbExclamation, "Error")
    Exit Sub
End Try

If sFound = "" Then
    MsgBox("Part Number '" & sPartNumber & "' not found in ERP data.", vbInformation, "Not Found")
    Exit Sub
End If

' --- Parse found data ---
Dim aData() As String = sFound.Split(",")
If aData.Length >= 4 Then
    Dim sDescription As String = aData(1).Trim()
    Dim sMaterial As String = aData(2).Trim()
    Dim sCost As String = aData(3).Trim()

    Try
        Dim oProps As PropertySet = oPartDoc.PropertySets.Item("Design Tracking Properties")

        Try
            oProps.Item("Description").Value = sDescription
        Catch
            oPartDoc.PropertySets.Item("Design Tracking Properties").Add(sDescription, "Description")
        End Try

        Try
            oProps.Item("Material").Value = sMaterial
        Catch
            oPartDoc.PropertySets.Item("Design Tracking Properties").Add(sMaterial, "Material")
        End Try

        Try
            oProps.Item("Unit Cost").Value = sCost
        Catch
            oPartDoc.PropertySets.Item("Design Tracking Properties").Add(sCost, "Unit Cost")
        End Try

        oPartDoc.Save()

        MsgBox("ERP data applied:" & vbCrLf & vbCrLf & _
               "Description: " & sDescription & vbCrLf & _
               "Material: " & sMaterial & vbCrLf & _
               "Unit Cost: " & sCost, vbInformation, "ERP Integration Demo")
    Catch ex As Exception
        MsgBox("Error updating iProperties: " & ex.Message, vbExclamation, "Error")
    End Try
Else
    MsgBox("Invalid data format in CSV.", vbExclamation, "Error")
End Try
