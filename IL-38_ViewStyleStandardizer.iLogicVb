'==============================================================================
' NAME:         Drawing View Style Standardizer
' AUTHOR:       Jugoslav Ilic
' DATE:         04.09.2026.
' VERSION:      1.0.0
' LICENSE:      MIT — free to use with attribution
' GITHUB:       github.com/iddj27510/iLogic-Library
'
' DESCRIPTION:
'   Standardizes drawing view styles according to a defined standard.
'
' PARAMETERS:
'   None — configured at the top of the script.
'
' ASSUMPTIONS:
'   Active document must be a Drawing document.
'
' TESTED ON:
'   Autodesk Inventor 2027
'==============================================================================

' ============================================================
' CONFIGURATION — edit before use
' ============================================================
Dim sTargetStyle As String = "Visible Lines"
Dim bFixAutomatically As Boolean = False
' ============================================================

' --- Context check ---
If Not (TypeOf ThisApplication.ActiveDocument Is DrawingDocument) Then
    MsgBox("Run this rule from a Drawing document.", vbExclamation, "Wrong Document Type")
    Exit Sub
End If

Dim oDrawDoc As DrawingDocument = ThisApplication.ActiveDocument

Dim sReport As String = "=== Drawing View Style Standardizer ===" & vbCrLf & vbCrLf
Dim nChanged As Integer = 0
Dim nTotal As Integer = 0

For Each oSheet As Sheet In oDrawDoc.Sheets
    For Each oView As DrawingView In oSheet.DrawingViews
        nTotal = nTotal + 1

        Try
            Dim sCurrentStyle As String = oView.Style.Name

            If sCurrentStyle <> sTargetStyle Then
                sReport &= "⚠ View on Sheet " & oSheet.Name & ": " & sCurrentStyle & " → " & sTargetStyle & vbCrLf

                If bFixAutomatically Then
                    oView.Style = oDrawDoc.StylesManager.DrawingViewStyles(sTargetStyle)
                    nChanged = nChanged + 1
                End If
            End If
        Catch
        End Try
    Next
Next

If bFixAutomatically Then
    sReport &= vbCrLf & "Changed: " & nChanged & " views."
Else
    sReport &= vbCrLf & "Views checked: " & nTotal & vbCrLf
    sReport &= "Views with non-standard style: " & nChanged & vbCrLf
    sReport &= "(Run with bFixAutomatically = True to fix)"
End If

MsgBox(sReport, vbInformation, "View Style Standardizer")
