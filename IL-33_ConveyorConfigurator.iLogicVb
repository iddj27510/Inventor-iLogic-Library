'==============================================================================
' NAME:         Conveyor Size Configurator
' AUTHOR:       Jugoslav Ilic
' DATE:         04.09.2026.
' VERSION:      1.0.0
' LICENSE:      MIT — free to use with attribution
' GITHUB:       github.com/iddj27510/iLogic-Library
'
' DESCRIPTION:
'   Parametric configurator for conveyor systems.
'   Directly from Wyma Solutions experience.
'
' PARAMETERS:
'   None — configured at the top of the script.
'
' ASSUMPTIONS:
'   Active document must be an Assembly document.
'
' TESTED ON:
'   Autodesk Inventor 2027
'==============================================================================

' ============================================================
' CONFIGURATION — edit before use
' ============================================================
Dim nMinLength As Double = 500
Dim nMaxLength As Double = 10000
Dim aWidths As New List(Of String) From {"300", "400", "500", "600", "800"}
Dim aBeltTypes As New List(Of String) From {"Flat", "Cleated", "Perforated"}
Dim aDriveLocations As New List(Of String) From {"Head", "Tail", "Center"}
Dim nMaxLoad As Double = 200
' ============================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument
Dim oParams As Parameters = oAsmDoc.ComponentDefinition.Parameters

' --- Get current values ---
Dim dLength As Double = 1500
Dim dWidth As Double = 400
Dim sBeltType As String = "Flat"
Dim sDriveLocation As String = "Head"
Dim dLoad As Double = 50

Try
    dLength = oParams.Item("Length").Value
Catch
End Try

Try
    dWidth = oParams.Item("Width").Value
Catch
End Try

Try
    sBeltType = oParams.Item("BeltType").Value.ToString()
Catch
End Try

Try
    sDriveLocation = oParams.Item("DriveLocation").Value.ToString()
Catch
End Try

Try
    dLoad = oParams.Item("DesignLoad").Value
Catch
End Try

' --- User input ---
Dim sMsg As String = "=== Conveyor Size Configurator ===" & vbCrLf & vbCrLf
sMsg &= "Current values:" & vbCrLf
sMsg &= "Length: " & dLength & " mm" & vbCrLf
sMsg &= "Width: " & dWidth & " mm" & vbCrLf
sMsg &= "Belt Type: " & sBeltType & vbCrLf
sMsg &= "Drive Location: " & sDriveLocation & vbCrLf
sMsg &= "Design Load: " & dLoad & " kg/m" & vbCrLf & vbCrLf
sMsg &= "Do you want to configure?"

If MsgBox(sMsg, vbYesNo + vbQuestion, "Conveyor Configurator") <> vbYes Then
    Exit Sub
End If

' --- Get new values ---
Dim sLength As String = InputBox("Length (mm) [" & nMinLength & "-" & nMaxLength & "]:", "Conveyor Configurator", dLength)
Dim sWidth As String = InputBox("Width (mm) [" & String.Join(", ", aWidths) & "]:", "Conveyor Configurator", dWidth)
Dim sBelt As String = InputBox("Belt Type [" & String.Join(", ", aBeltTypes) & "]:", "Conveyor Configurator", sBeltType)
Dim sDrive As String = InputBox("Drive Location [" & String.Join(", ", aDriveLocations) & "]:", "Conveyor Configurator", sDriveLocation)
Dim sLoad As String = InputBox("Design Load (kg/m) [max " & nMaxLoad & "]:", "Conveyor Configurator", dLoad)

' --- Validate ---
Dim dNewLength As Double = Val(sLength)
If dNewLength < nMinLength Or dNewLength > nMaxLength Then
    MsgBox("Length must be between " & nMinLength & " and " & nMaxLength & " mm.", vbExclamation, "Validation Error")
    Exit Sub
End If

If Not aWidths.Contains(sWidth) Then
    MsgBox("Width must be one of: " & String.Join(", ", aWidths), vbExclamation, "Validation Error")
    Exit Sub
End If

If Not aBeltTypes.Contains(sBelt) Then
    MsgBox("Belt Type must be one of: " & String.Join(", ", aBeltTypes), vbExclamation, "Validation Error")
    Exit Sub
End If

If Not aDriveLocations.Contains(sDrive) Then
    MsgBox("Drive Location must be one of: " & String.Join(", ", aDriveLocations), vbExclamation, "Validation Error")
    Exit Sub
End If

Dim dNewLoad As Double = Val(sLoad)
If dNewLoad > nMaxLoad Then
    MsgBox("Design Load cannot exceed " & nMaxLoad & " kg/m.", vbExclamation, "Validation Error")
    Exit Sub
End If

' --- Apply changes ---
Try
    oParams.Item("Length").Value = dNewLength
    oParams.Item("Width").Value = Val(sWidth)
    oParams.Item("BeltType").Value = sBelt
    oParams.Item("DriveLocation").Value = sDrive
    oParams.Item("DesignLoad").Value = dNewLoad

    ThisApplication.ActiveDocument.Update()

    Dim sDesc As String = "CONV-" & dNewLength & "x" & sWidth & "-" & sBelt & "-" & sDrive & "-" & dNewLoad & "KGM"

    Try
        Dim oProps As PropertySet = oAsmDoc.PropertySets.Item("Design Tracking Properties")
        oProps.Item("Description").Value = sDesc
    Catch
        oAsmDoc.PropertySets.Item("Design Tracking Properties").Add(sDesc, "Description")
    End Try

    oAsmDoc.Save()

    MsgBox("Conveyor configured successfully!" & vbCrLf & vbCrLf & "Description: " & sDesc, vbInformation, "Conveyor Configurator")

Catch ex As Exception
    MsgBox("Error: " & ex.Message, vbExclamation, "Error")
End Try
