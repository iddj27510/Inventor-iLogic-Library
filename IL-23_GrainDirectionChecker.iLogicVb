'==============================================================================
' NAME:         Grain Direction Checker
' AUTHOR:       Jugoslav Ilic
' DATE:         04.09.2026.
' VERSION:      1.0.0
' LICENSE:      MIT — free to use with attribution
' GITHUB:       github.com/iddj27510/iLogic-Library
'
' DESCRIPTION:
'   Checks grain direction in sheet metal parts.
'   Warns if the angle is outside tolerance.
'
' PARAMETERS:
'   None — configured at the top of the script.
'
' ASSUMPTIONS:
'   Active document must be a Part document (sheet metal).
'
' TESTED ON:
'   Autodesk Inventor 2027
'==============================================================================

' ============================================================
' CONFIGURATION — edit before use
' ============================================================
Dim dMaxAngle As Double = 5.0   ' Maximum allowed angle in degrees
' ============================================================

' --- Context check ---
If Not (TypeOf ThisApplication.ActiveDocument Is PartDocument) Then
    MsgBox("Run this rule from a Part document.", vbExclamation, "Wrong Document Type")
    Exit Sub
End If

Dim oPartDoc As PartDocument = ThisApplication.ActiveDocument

' --- Check if sheet metal ---
If Not (TypeOf oPartDoc.ComponentDefinition Is SheetMetalComponentDefinition) Then
    MsgBox("This is not a sheet metal part.", vbInformation, "Not Sheet Metal")
    Exit Sub
End If

Dim oSMDef As SheetMetalComponentDefinition = oPartDoc.ComponentDefinition

' --- Check if flat pattern exists ---
If Not oSMDef.HasFlatPattern Then
    MsgBox("Flat pattern does not exist.", vbInformation, "No Flat Pattern")
    Exit Sub
End If

' --- Get flat pattern orientation ---
Try
    Dim oFlatPattern As FlatPattern = oSMDef.FlatPattern
    Dim oWorkPlane As WorkPlane = oFlatPattern.FlatPatternFace.WorkPlane

    Dim oNormal As UnitVector = oWorkPlane.Plane.Normal

    Dim dAngle As Double = Math.Abs(oNormal.AngleTo(ThisApplication.TransientObjects.CreateUnitVector(1, 0, 0)) * 180 / Math.PI)

    If dAngle > dMaxAngle Then
        MsgBox("Grain direction angle: " & Math.Round(dAngle, 1) & "°" & vbCrLf & _
               "Maximum allowed: " & dMaxAngle & "°" & vbCrLf & vbCrLf & _
               "Grain direction may be incorrect!", vbExclamation, "Grain Direction Checker")
    Else
        MsgBox("Grain direction OK: " & Math.Round(dAngle, 1) & "°", vbInformation, "Grain Direction Checker")
    End If

Catch ex As Exception
    MsgBox("Could not check grain direction: " & ex.Message, vbExclamation, "Error")
End Try
