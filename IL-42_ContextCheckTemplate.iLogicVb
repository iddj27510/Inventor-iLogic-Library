'==============================================================================
' NAME:         Assembly Context Check Template
' AUTHOR:       Jugoslav Ilic
' DATE:         04.09.2026.
' VERSION:      1.0.0
' LICENSE:      MIT — free to use with attribution
' GITHUB:       github.com/iddj27510/iLogic-Library
'
' DESCRIPTION:
'   Reusable template for context checking at the start of each rule.
'   Prevents "Object reference not set" errors.
'
' PARAMETERS:
'   None — configured at the top of the script.
'
' ASSUMPTIONS:
'   None — used as a helper.
'
' TESTED ON:
'   Autodesk Inventor 2027
'
' NOTES:
'   Copy this code to the beginning of every assembly rule.
'==============================================================================

' ============================================================
' CONFIGURATION — edit before use
' ============================================================
Dim sRequiredType As String = "Assembly"   ' "Assembly", "Part", "Drawing"
' ============================================================

' --- Context check function ---
Function CheckContext(sRequiredType As String) As Boolean
    Dim oDoc As Document = ThisApplication.ActiveDocument

    If oDoc Is Nothing Then
        MsgBox("No active document.", vbExclamation, "Context Error")
        CheckContext = False
        Exit Function
    End If

    Select Case sRequiredType
        Case "Assembly"
            If Not (TypeOf oDoc Is AssemblyDocument) Then
                MsgBox("This rule must be run from an Assembly document." & vbCrLf & _
                       "Current type: " & oDoc.DocumentType.ToString(), _
                       vbExclamation, "Wrong Document Type")
                CheckContext = False
                Exit Function
            End If
        Case "Part"
            If Not (TypeOf oDoc Is PartDocument) Then
                MsgBox("This rule must be run from a Part document." & vbCrLf & _
                       "Current type: " & oDoc.DocumentType.ToString(), _
                       vbExclamation, "Wrong Document Type")
                CheckContext = False
                Exit Function
            End If
        Case "Drawing"
            If Not (TypeOf oDoc Is DrawingDocument) Then
                MsgBox("This rule must be run from a Drawing document." & vbCrLf & _
                       "Current type: " & oDoc.DocumentType.ToString(), _
                       vbExclamation, "Wrong Document Type")
                CheckContext = False
                Exit Function
            End If
        Case Else
            CheckContext = True
            Exit Function
    End Select

    CheckContext = True
End Function

' --- Usage example ---
' If Not CheckContext("Assembly") Then Exit Sub

' --- Proceed with rule logic ---
MsgBox("Context check passed. Running rule...", vbInformation, "Context Check OK")
