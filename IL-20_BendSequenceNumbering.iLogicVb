'==============================================================================
' NAME:         Bend Sequence Numbering
' AUTHOR:       Jugoslav Ilic
' DATE:         04.09.2026.
' VERSION:      1.0.0
' LICENSE:      MIT — free to use with attribution
' GITHUB:       github.com/iddj27510/iLogic-Library
'
' DESCRIPTION:
'   Numbers bend features in a sheet metal part from 1 to N.
'   Adds the number as an iProperty "Bend Sequence".
'
' PARAMETERS:
'   None — configured at the top of the script.
'
' ASSUMPTIONS:
'   Active document must be a Part document (sheet metal).
'
' TESTED ON:
'   Autodesk Inventor 2027
'
' NOTES:
'   Bend order is based on feature creation order in the model.
'==============================================================================

' ============================================================
' CONFIGURATION — edit before use
' ============================================================
Dim sSequenceProperty As String = "Bend Sequence"
' ============================================================

' --- Context check ---
If Not (TypeOf ThisApplication.ActiveDocument Is PartDocument) Then
    MsgBox("Run this rule from a Part document.", vbExclamation, "Wrong Document Type")
    Exit Sub
End If

Dim oPartDoc As PartDocument = ThisApplication.ActiveDocument

' --- Check if sheet metal ---
If Not (TypeOf oPartDoc.ComponentDefinition Is SheetMetalComponentDefinition) Then
    MsgBox("This is not a sheet metal part.", vbInformation, "Not Sheet Metal")
    Exit Sub
End If

Dim oSMDef As SheetMetalComponentDefinition = oPartDoc.ComponentDefinition
Dim oFeatures As Features = oSMDef.Features

Dim nCount As Integer = 0
Dim sLog As String = "=== Bend Sequence Numbering ===" & vbCrLf & vbCrLf

For Each oFeature As Feature In oFeatures
    Try
        Dim sFeatureType As String = oFeature.Type.ToString()
        If sFeatureType.Contains("Bend") Or sFeatureType.Contains("Flange") Then
            nCount = nCount + 1

            Try
                Dim oProps As PropertySet = oPartDoc.PropertySets.Item("Design Tracking Properties")
                Try
                    oProps.Item(sSequenceProperty).Value = nCount.ToString()
                Catch
                    oPartDoc.PropertySets.Item("Design Tracking Properties").Add(nCount.ToString(), sSequenceProperty)
                End Try
            Catch
            End Try

            sLog &= nCount & ". " & oFeature.Name & vbCrLf
        End If
    Catch
    End Try
Next

sLog &= vbCrLf & "Total bends: " & nCount

oPartDoc.Save()

MsgBox(sLog, vbInformation, "Bend Sequence Numbering")
