'==============================================================================
' NAME:         Assembly Occurrence Traversal Helper
' AUTHOR:       Jugoslav Ilic
' DATE:         04.09.2026.
' VERSION:      1.0.0
' LICENSE:      MIT — free to use with attribution
' GITHUB:       github.com/iddj27510/iLogic-Library
'
' DESCRIPTION:
'   Reusable template for recursive assembly scanning.
'   Used as the foundation for all assembly-scanning rules.
'
' PARAMETERS:
'   None — configured at the top of the script.
'
' ASSUMPTIONS:
'   Active document must be an Assembly document.
'
' TESTED ON:
'   Autodesk Inventor 2027
'
' NOTES:
'   This is a helper template — copy it into other rules.
'==============================================================================

' ============================================================
' CONFIGURATION — edit before use
' ============================================================
Dim bRecursive As Boolean = True
Dim nMaxDepth As Integer = 0    ' 0 = unlimited
Dim sFilterType As String = "All"   ' "All", "Parts", "Assemblies", "SheetMetal"
' ============================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument
Dim oOccs As ComponentOccurrences = oAsmDoc.ComponentDefinition.Occurrences

Dim sLog As String = "=== Assembly Occurrence Traversal ===" & vbCrLf & vbCrLf
Dim nCount As Integer = 0

TraverseAssembly(oOccs, sLog, nCount, 0)

sLog &= vbCrLf & "Total occurrences: " & nCount

MsgBox(sLog, vbInformation, "Traversal Helper")

'==============================================================================
' CORE TRAVERSAL FUNCTION
'==============================================================================

Sub TraverseAssembly(oOccs As ComponentOccurrences, ByRef sLog As String, ByRef nCount As Integer, nLevel As Integer)
    If nMaxDepth > 0 And nLevel >= nMaxDepth Then
        Return
    End If

    Dim oOcc As ComponentOccurrence
    For Each oOcc In oOccs
        Try
            If oOcc.DefinitionDocumentType = DocumentTypeEnum.kVirtualComponentDocumentObject Then
                Continue For
            End If

            Dim bInclude As Boolean = False
            Select Case sFilterType
                Case "Parts"
                    bInclude = (oOcc.DefinitionDocumentType = DocumentTypeEnum.kPartDocumentObject)
                Case "Assemblies"
                    bInclude = (oOcc.DefinitionDocumentType = DocumentTypeEnum.kAssemblyDocumentObject)
                Case "SheetMetal"
                    If oOcc.DefinitionDocumentType = DocumentTypeEnum.kPartDocumentObject Then
                        Try
                            Dim oPart As PartDocument = oOcc.Definition.Document
                            bInclude = (TypeOf oPart.ComponentDefinition Is SheetMetalComponentDefinition)
                        Catch
                            bInclude = False
                        End Try
                    End If
                Case Else
                    bInclude = True
            End Select

            If bInclude Then
                nCount = nCount + 1
                Dim sIndent As String = New String(" ", nLevel * 2)
                Dim sType As String = ""

                If oOcc.DefinitionDocumentType = DocumentTypeEnum.kPartDocumentObject Then
                    sType = "Part"
                ElseIf oOcc.DefinitionDocumentType = DocumentTypeEnum.kAssemblyDocumentObject Then
                    sType = "Assembly"
                End If

                sLog &= sIndent & nCount & ". " & oOcc.Name & " (" & sType & ")" & vbCrLf
            End If

            If bRecursive And oOcc.DefinitionDocumentType = DocumentTypeEnum.kAssemblyDocumentObject Then
                Dim oSubAsm As AssemblyDocument = oOcc.Definition.Document
                TraverseAssembly(oSubAsm.ComponentDefinition.Occurrences, sLog, nCount, nLevel + 1)
            End If

        Catch ex As Exception
            sLog &= "  ! Error: " & oOcc.Name & " - " & ex.Message & vbCrLf
        End Try
    Next
End Sub
