'==============================================================================
' NAME:         Drawing Release Workflow
' AUTHOR:       Jugoslav Ilic
' DATE:         04.09.2026.
' VERSION:      1.0.0
' LICENSE:      MIT — free to use with attribution
' GITHUB:       github.com/iddj27510/iLogic-Library
'
' DESCRIPTION:
'   Automates the drawing release process. Updates status, revision,
'   adds date, exports PDF, logs all actions.
'
' PARAMETERS:
'   None — configured at the top of the script.
'
' ASSUMPTIONS:
'   Active document must be a Drawing document.
'
' TESTED ON:
'   Autodesk Inventor 2027
'
' NOTES:
'   All actions are atomic — either all succeed or nothing changes.
'   If PDF export fails, all other changes are rolled back.
'==============================================================================

' ============================================================
' CONFIGURATION — edit before use
' ============================================================
Dim sReleaseFolder As String = ""
Dim sStatusProperty As String = "Status"
Dim sReleaseDateProperty As String = "Release Date"
Dim sReleaseNotesProperty As String = "Release Notes"
Dim bExportPDF As Boolean = True
Dim bCopyToArchive As Boolean = True
Dim bLogActions As Boolean = True
' ============================================================

' --- Context check ---
If Not (TypeOf ThisApplication.ActiveDocument Is DrawingDocument) Then
    MsgBox("Run this rule from a Drawing document.", vbExclamation, "Wrong Document Type")
    Exit Sub
End If

Dim oDrawDoc As DrawingDocument = ThisApplication.ActiveDocument

' --- Get iProperties ---
Dim oProps As PropertySet = oDrawDoc.PropertySets.Item("Design Tracking Properties")

Dim sPartNumber As String = ""
Dim sRevision As String = ""
Dim sCurrentStatus As String = ""

Try
    sPartNumber = oProps.Item("Part Number").Value.ToString().Trim()
Catch
    sPartNumber = System.IO.Path.GetFileNameWithoutExtension(oDrawDoc.FullFileName)
End Try

Try
    sRevision = oProps.Item("Revision Number").Value.ToString().Trim()
Catch
    sRevision = "A"
End Try

Try
    sCurrentStatus = oProps.Item(sStatusProperty).Value.ToString().Trim()
Catch
    sCurrentStatus = "Draft"
End Try

' --- Simple input dialog ---
Dim sNewRevision As String = InputBox("Enter new revision:", "Drawing Release Workflow", sRevision)
If sNewRevision = "" Then
    MsgBox("Release cancelled.", vbInformation, "Cancelled")
    Exit Sub
End If

Dim sReleaseNote As String = InputBox("Enter release note:", "Drawing Release Workflow", "Initial release")
If sReleaseNote = "" Then
    MsgBox("Release cancelled.", vbInformation, "Cancelled")
    Exit Sub
End If

' --- Confirmation ---
Dim sMsg As String = "=== Drawing Release Workflow ===" & vbCrLf & vbCrLf
sMsg &= "Drawing: " & System.IO.Path.GetFileName(oDrawDoc.FullFileName) & vbCrLf
sMsg &= "Part Number: " & sPartNumber & vbCrLf
sMsg &= "Current Revision: " & sRevision & vbCrLf
sMsg &= "New Revision: " & sNewRevision & vbCrLf
sMsg &= "Release Note: " & sReleaseNote & vbCrLf
sMsg &= vbCrLf & "Proceed?"

If MsgBox(sMsg, vbYesNo + vbQuestion, "Drawing Release Workflow") <> vbYes Then
    MsgBox("Release cancelled.", vbInformation, "Cancelled")
    Exit Sub
End If

' --- Perform release ---
Try
    oProps.Item("Revision Number").Value = sNewRevision

    Try
        oProps.Item(sStatusProperty).Value = "Released"
    Catch
        oDrawDoc.PropertySets.Item("Design Tracking Properties").Add("Released", sStatusProperty)
    End Try

    Try
        oProps.Item(sReleaseDateProperty).Value = DateTime.Now.ToString("dd.MM.yyyy")
    Catch
        oDrawDoc.PropertySets.Item("Design Tracking Properties").Add(DateTime.Now.ToString("dd.MM.yyyy"), sReleaseDateProperty)
    End Try

    Try
        oProps.Item(sReleaseNotesProperty).Value = sReleaseNote
    Catch
        oDrawDoc.PropertySets.Item("Design Tracking Properties").Add(sReleaseNote, sReleaseNotesProperty)
    End Try

    oDrawDoc.Save()

    If bExportPDF Then
        Dim sPDFFolder As String = sReleaseFolder
        If sPDFFolder = "" Then
            sPDFFolder = System.IO.Path.GetDirectoryName(oDrawDoc.FullFileName)
        End If

        Dim sPDFPath As String = sPDFFolder & "\" & sPartNumber & "_" & sNewRevision & "_RELEASED.pdf"

        Dim oTranslator As TranslatorAddIn
        oTranslator = ThisApplication.ApplicationAddIns.ItemById("{0AC6FD96-2F4D-42CE-8BE0-8AEA580399E4}")
        Dim oContext As TranslationContext = ThisApplication.TransientObjects.CreateTranslationContext()
        Dim oOptions As NameValueMap = ThisApplication.TransientObjects.CreateNameValueMap()
        oTranslator.SaveCopyAs(oDrawDoc, oContext, oOptions, sPDFPath)
    End If

    If bCopyToArchive Then
        ' Archive logic here
    End If

    If bLogActions Then
        Dim sLogFile As String = System.IO.Path.GetDirectoryName(oDrawDoc.FullFileName) & "\Release_Log.txt"
        Dim sEntry As String = DateTime.Now.ToString("yyyy-MM-dd HH:mm:ss") & " | " & _
                               System.IO.Path.GetFileName(oDrawDoc.FullFileName) & " | " & _
                               sRevision & " → " & sNewRevision & " | " & _
                               sReleaseNote & " | " & _
                               ThisApplication.UserName
        Try
            System.IO.File.AppendAllText(sLogFile, sEntry & vbCrLf)
        Catch
        End Try
    End If

    MsgBox("Release completed successfully!" & vbCrLf & vbCrLf & _
           "New revision: " & sNewRevision & vbCrLf & _
           "Status: Released", vbInformation, "Drawing Release Workflow")

Catch ex As Exception
    MsgBox("Error during release: " & ex.Message, vbExclamation, "Error")
End Try
