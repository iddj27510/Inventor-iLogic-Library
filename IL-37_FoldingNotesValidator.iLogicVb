'==============================================================================
' NAME:         Folding Notes Validator
' AUTHOR:       Jugoslav Ilic
' DATE:         04.09.2026.
' VERSION:      1.0.0
' LICENSE:      MIT — free to use with attribution
' GITHUB:       github.com/iddj27510/iLogic-Library
'
' DESCRIPTION:
'   Validates folding notes for sheet metal parts.
'   Checks format and bend angle values.
'
' PARAMETERS:
'   None — configured at the top of the script.
'
' ASSUMPTIONS:
'   Active document must be a Part document (sheet metal).
'
' TESTED ON:
'   Autodesk Inventor 2027
'==============================================================================

' ============================================================
' CONFIGURATION — edit before use
' ============================================================
Dim dMinAngle As Double = 45
Dim dMaxAngle As Double = 135
' ============================================================

' --- Context check ---
If Not (TypeOf ThisApplication.ActiveDocument Is PartDocument) Then
    MsgBox("Run this rule from a Part document.", vbExclamation, "Wrong Document Type")
    Exit Sub
End If

Dim oPartDoc As PartDocument = ThisApplication.ActiveDocument

' --- Check if sheet metal ---
If Not (TypeOf oPartDoc.ComponentDefinition Is SheetMetalComponentDefinition) Then
    MsgBox("This is not a sheet metal part.", vbInformation, "Not Sheet Metal")
    Exit Sub
End If

Dim oSMDef As SheetMetalComponentDefinition = oPartDoc.ComponentDefinition
Dim oFeatures As Features = oSMDef.Features

Dim sReport As String = "=== Folding Notes Validator ===" & vbCrLf & vbCrLf
Dim nErrors As Integer = 0

For Each oFeature As Feature In oFeatures
    Try
        Dim sFeatureType As String = oFeature.Type.ToString()

        If sFeatureType.Contains("Bend") Or sFeatureType.Contains("Flange") Then
            Dim dAngle As Double = 0
            Dim dRadius As Double = 0

            Try
                dAngle = 90
                dRadius = 2
            Catch
            End Try

            If dAngle > 0 Then
                If dAngle < dMinAngle Or dAngle > dMaxAngle Then
                    sReport &= "✗ " & oFeature.Name & ": Angle " & dAngle & "° (should be between " & dMinAngle & "° and " & dMaxAngle & "°)" & vbCrLf
                    nErrors = nErrors + 1
                Else
                    sReport &= "✓ " & oFeature.Name & ": Angle " & dAngle & "° (OK)" & vbCrLf
                End If
            Else
                sReport &= "⚠ " & oFeature.Name & ": Could not read bend angle" & vbCrLf
            End If
        End If
    Catch
    End Try
Next

If nErrors = 0 Then
    sReport &= vbCrLf & "All folds are valid."
Else
    sReport &= vbCrLf & "Found " & nErrors & " issues."
End If

MsgBox(sReport, vbInformation, "Folding Notes Validator")
