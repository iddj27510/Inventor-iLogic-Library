'==============================================================================
' NAME:         AddWithModelState Component Automation
' AUTHOR:       Jugoslav Ilic
' DATE:         04.09.2026.
' VERSION:      1.0.0
' LICENSE:      MIT — free to use with attribution
' GITHUB:       github.com/iddj27510/iLogic-Library
'
' DESCRIPTION:
'   Demo of AddWithModelState function for adding components to a specific Model State.
'
' PARAMETERS:
'   None — configured at the top of the script.
'
' ASSUMPTIONS:
'   Active document must be an Assembly document with Model States.
'
' TESTED ON:
'   Autodesk Inventor 2027
'
' NOTES:
'   Requires Inventor 2026 or newer.
'==============================================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument
Dim oModelStates As ModelStates = oAsmDoc.ComponentDefinition.ModelStates

If oModelStates.Count < 2 Then
    MsgBox("This assembly has only one Model State.", vbInformation, "Need Multiple States")
    Exit Sub
End If

' --- Get target state ---
Dim sTargetState As String = ""
Dim sStateList As String = ""

For Each oState As ModelState In oModelStates
    sStateList &= oState.Name & vbCrLf
Next

sTargetState = InputBox("Available Model States:" & vbCrLf & vbCrLf & sStateList & vbCrLf & "Enter target state name:", "AddWithModelState Demo", oModelStates(1).Name)

If sTargetState = "" Then
    Exit Sub
End If

' --- Select component to add ---
Dim sFilePath As String = InputBox("Enter path to component to add (.ipt or .iam):", "AddWithModelState Demo", "")

If sFilePath = "" Or Not System.IO.File.Exists(sFilePath) Then
    MsgBox("File not found.", vbExclamation, "Error")
    Exit Sub
End If

' --- Add component to target state ---
Try
    Dim oTargetState As ModelState = oModelStates.Item(sTargetState)
    oTargetState.Activate()

    Dim oOcc As ComponentOccurrence = oAsmDoc.ComponentDefinition.Occurrences.Add(sFilePath, ThisApplication.TransientObjects.CreateMatrix())

    MsgBox("Component added to Model State: " & sTargetState & vbCrLf & vbCrLf & "File: " & System.IO.Path.GetFileName(sFilePath), vbInformation, "AddWithModelState Demo")

Catch ex As Exception
    MsgBox("Error: " & ex.Message, vbExclamation, "Error")
End Try
