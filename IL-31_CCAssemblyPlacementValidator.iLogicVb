'==============================================================================
' NAME:         CC Assembly Placement Validator
' AUTHOR:       Jugoslav Ilic
' DATE:         04.09.2026.
' VERSION:      1.0.0
' LICENSE:      MIT — free to use with attribution
' GITHUB:       github.com/iddj27510/iLogic-Library
'
' DESCRIPTION:
'   Validates CC assembly references in an assembly.
'   Detects broken links for CC assemblies.
'
' PARAMETERS:
'   None — configured at the top of the script.
'
' ASSUMPTIONS:
'   Active document must be an Assembly document.
'   Inventor 2027 ONLY (CC Assembly support)
'
' TESTED ON:
'   Autodesk Inventor 2027
'==============================================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument

Dim errors As New List(Of String)
Dim warnings As New List(Of String)

ScanCCAssembly(oAsmDoc.ComponentDefinition.Occurrences, errors, warnings, 0)

Dim report As String = "=== CC Assembly Placement Validator ===" & vbCrLf & vbCrLf

If errors.Count > 0 Then
    report &= "ERRORS (" & errors.Count & "):" & vbCrLf
    For Each s As String In errors
        report &= "  ! " & s & vbCrLf
    Next
Else
    report &= "No errors found." & vbCrLf
End If

If warnings.Count > 0 Then
    report &= vbCrLf & "WARNINGS (" & warnings.Count & "):" & vbCrLf
    For Each s As String In warnings
        report &= "  - " & s & vbCrLf
    Next
End If

MsgBox(report, vbInformation, "CC Assembly Validator")

Sub ScanCCAssembly(oOccs As ComponentOccurrences, errors As List(Of String), warnings As List(Of String), nLevel As Integer)
    Dim oOcc As ComponentOccurrence
    For Each oOcc In oOccs
        Try
            If oOcc.DefinitionDocumentType = DocumentTypeEnum.kVirtualComponentDocumentObject Then
                Continue For
            End If

            If oOcc.DefinitionDocumentType = DocumentTypeEnum.kAssemblyDocumentObject Then
                Dim oSubAsm As AssemblyDocument = oOcc.Definition.Document

                Try
                    Dim oCC As Inventor.Property = oSubAsm.PropertySets.Item("Design Tracking Properties").Item("Content Center Member")
                    If oCC IsNot Nothing Then
                        Try
                            Dim sPath As String = oSubAsm.FullFileName
                            If Not System.IO.File.Exists(sPath) Then
                                errors.Add(oOcc.Name & " — CC Assembly link is broken")
                            End If
                        Catch
                            errors.Add(oOcc.Name & " — CC Assembly link is broken")
                        End Try
                    End If
                Catch
                End Try

                ScanCCAssembly(oSubAsm.ComponentDefinition.Occurrences, errors, warnings, nLevel + 1)
            End If
        Catch ex As Exception
            errors.Add(oOcc.Name & " — " & ex.Message)
        End Try
    Next
End Sub
