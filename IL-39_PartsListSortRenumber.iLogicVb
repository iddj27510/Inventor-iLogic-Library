'==============================================================================
' NAME:         Parts List Sort & Renumber
' AUTHOR:       Jugoslav Ilic
' DATE:         04.09.2026.
' VERSION:      1.0.0
' LICENSE:      MIT — free to use with attribution
' GITHUB:       github.com/iddj27510/iLogic-Library
'
' DESCRIPTION:
'   Sorts Parts List by Part Number and renumbers balloons.
'
' PARAMETERS:
'   None — configured at the top of the script.
'
' ASSUMPTIONS:
'   Active document must be a Drawing document.
'
' TESTED ON:
'   Autodesk Inventor 2027
'
' NOTES:
'   GitHub only - small developer (MvB Solutions) does the same task.
'==============================================================================

' ============================================================
' CONFIGURATION — edit before use
' ============================================================
Dim sSortColumn As String = "Part Number"
Dim bUpdateBalloons As Boolean = True
' ============================================================

' --- Context check ---
If Not (TypeOf ThisApplication.ActiveDocument Is DrawingDocument) Then
    MsgBox("Run this rule from a Drawing document.", vbExclamation, "Wrong Document Type")
    Exit Sub
End If

Dim oDrawDoc As DrawingDocument = ThisApplication.ActiveDocument

' --- Find Parts List ---
Dim oPartsList As PartsList = Nothing

For Each oSheet As Sheet In oDrawDoc.Sheets
    For Each oPL As PartsList In oSheet.PartsLists
        oPartsList = oPL
        Exit For
    Next
    If oPartsList IsNot Nothing Then Exit For
Next

If oPartsList Is Nothing Then
    MsgBox("No Parts List found in drawing.", vbInformation, "Not Found")
    Exit Sub
End If

' --- Sort by Part Number ---
Try
    Dim oSortColumns As PartsListSortColumns = oPartsList.SortColumns
    oSortColumns.Clear()

    Dim oCol As PartsListColumn = oPartsList.PartsListColumns.Item(sSortColumn)
    If oCol IsNot Nothing Then
        oSortColumns.Add(oCol, PartsListSortOrderEnum.kAscendingSortOrder)
    End If

    oPartsList.Update()

    If bUpdateBalloons Then
        For Each oSheet As Sheet In oDrawDoc.Sheets
            For Each oView As DrawingView In oSheet.DrawingViews
                Try
                    oView.Balloons.Renumber()
                Catch
                End Try
            Next
        Next
    End If

    MsgBox("Parts List sorted by " & sSortColumn & " and renumbered.", vbInformation, "Sort Complete")

Catch ex As Exception
    MsgBox("Error: " & ex.Message, vbExclamation, "Error")
End Try
