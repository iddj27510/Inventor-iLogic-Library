'==============================================================================
' NAME:         Drawing Scale Standardizer ISO 5455
' AUTHOR:       Jugoslav Ilic
' DATE:         04.09.2026.
' VERSION:      1.0.0
' LICENSE:      MIT — free to use with attribution
' GITHUB:       github.com/iddj27510/iLogic-Library
'
' DESCRIPTION:
'   Checks and standardizes scale values according to ISO 5455.
'   Allowed values: 1:1, 1:2, 1:5, 1:10, 2:1, 5:1, 10:1
'
' PARAMETERS:
'   None — configured at the top of the script.
'
' ASSUMPTIONS:
'   Active document must be a Drawing document.
'
' TESTED ON:
'   Autodesk Inventor 2027
'==============================================================================

' ============================================================
' CONFIGURATION — edit before use
' ============================================================
Dim aAllowedScales As New List(Of String) From {"1:1", "1:2", "1:5", "1:10", "2:1", "5:1", "10:1"}
Dim bFixAutomatically As Boolean = False
' ============================================================

' --- Context check ---
If Not (TypeOf ThisApplication.ActiveDocument Is DrawingDocument) Then
    MsgBox("Run this rule from a Drawing document.", vbExclamation, "Wrong Document Type")
    Exit Sub
End If

Dim oDrawDoc As DrawingDocument = ThisApplication.ActiveDocument
Dim sReport As String = "=== Drawing Scale Standardizer ISO 5455 ===" & vbCrLf & vbCrLf
Dim nFixed As Integer = 0

For Each oSheet As Sheet In oDrawDoc.Sheets
    For Each oView As DrawingView In oSheet.DrawingViews
        Dim sScale As String = oView.ScaleString
        Dim bValid As Boolean = False

        For Each sAllowed As String In aAllowedScales
            If sScale = sAllowed Then
                bValid = True
                Exit For
            End If
        Next

        If Not bValid Then
            sReport &= "⚠ View on Sheet " & oSheet.Name & ": Scale = " & sScale & " (not ISO 5455)" & vbCrLf

            If bFixAutomatically Then
                Dim dCurrent As Double = oView.Scale
                Dim dClosest As Double = 1.0
                Dim sClosest As String = "1:1"
                Dim dMinDiff As Double = 9999

                For Each sAllowed As String In aAllowedScales
                    Dim dAllowed As Double
                    If sAllowed.Contains(":") Then
                        Dim parts() As String = sAllowed.Split(":")
                        dAllowed = Double.Parse(parts(0)) / Double.Parse(parts(1))
                    Else
                        dAllowed = Double.Parse(sAllowed)
                    End If

                    Dim dDiff As Double = Math.Abs(dCurrent - dAllowed)
                    If dDiff < dMinDiff Then
                        dMinDiff = dDiff
                        dClosest = dAllowed
                        sClosest = sAllowed
                    End If
                Next

                oView.Scale = dClosest
                nFixed = nFixed + 1
                sReport &= "  → Fixed to: " & sClosest & vbCrLf
            End If
        End If
    Next
Next

If nFixed > 0 Then
    sReport &= vbCrLf & "Fixed: " & nFixed & " views."
ElseIf Not bFixAutomatically Then
    sReport &= vbCrLf & "No issues found (or run with auto-fix enabled)."
End If

MsgBox(sReport, vbInformation, "Drawing Scale Standardizer")
