'==============================================================================
' NAME:         K-Factor Validator Per Material
' AUTHOR:       Jugoslav Ilic
' DATE:         04.09.2026.
' VERSION:      1.0.0
' LICENSE:      MIT — free to use with attribution
' GITHUB:       github.com/iddj27510/iLogic-Library
'
' DESCRIPTION:
'   Validates K-Factor value against material and thickness.
'   Detects values outside the expected range.
'
' PARAMETERS:
'   None — configured at the top of the script.
'
' ASSUMPTIONS:
'   Active document must be a Part document (sheet metal).
'
' TESTED ON:
'   Autodesk Inventor 2027
'==============================================================================

' ============================================================
' CONFIGURATION — edit before use
' ============================================================
Dim aKFactorTable As New List(Of Dictionary(Of String, String)) From {
    New Dictionary(Of String, String) From {{"Material", "S235"}, {"Thickness", "2"}, {"Min", "0.38"}, {"Max", "0.44"}},
    New Dictionary(Of String, String) From {{"Material", "S235"}, {"Thickness", "3"}, {"Min", "0.40"}, {"Max", "0.46"}},
    New Dictionary(Of String, String) From {{"Material", "SS304"}, {"Thickness", "2"}, {"Min", "0.42"}, {"Max", "0.48"}},
    New Dictionary(Of String, String) From {{"Material", "SS304"}, {"Thickness", "3"}, {"Min", "0.44"}, {"Max", "0.50"}},
    New Dictionary(Of String, String) From {{"Material", "AL5052"}, {"Thickness", "2"}, {"Min", "0.38"}, {"Max", "0.44"}},
    New Dictionary(Of String, String) From {{"Material", "AL5052"}, {"Thickness", "3"}, {"Min", "0.40"}, {"Max", "0.46"}}
}
' ============================================================

' --- Context check ---
If Not (TypeOf ThisApplication.ActiveDocument Is PartDocument) Then
    MsgBox("Run this rule from a Part document.", vbExclamation, "Wrong Document Type")
    Exit Sub
End If

Dim oPartDoc As PartDocument = ThisApplication.ActiveDocument

' --- Check if sheet metal ---
If Not (TypeOf oPartDoc.ComponentDefinition Is SheetMetalComponentDefinition) Then
    MsgBox("This is not a sheet metal part.", vbInformation, "Not Sheet Metal")
    Exit Sub
End If

Dim oSMDef As SheetMetalComponentDefinition = oPartDoc.ComponentDefinition

' --- Get material and thickness ---
Dim sMaterial As String = ""
Dim dThickness As Double = oSMDef.Thickness

Try
    sMaterial = oPartDoc.PropertySets.Item("Design Tracking Properties").Item("Material").Value.ToString().Trim()
Catch
    sMaterial = "S235"
End Try

' --- Get K-Factor ---
Dim dKFactor As Double = oSMDef.KFactor

' --- Validate ---
Dim bFound As Boolean = False
Dim dMin As Double = 0.35
Dim dMax As Double = 0.50

For Each dict As Dictionary(Of String, String) In aKFactorTable
    If dict("Material") = sMaterial And dict("Thickness") = Math.Round(dThickness, 0).ToString() Then
        dMin = Double.Parse(dict("Min"))
        dMax = Double.Parse(dict("Max"))
        bFound = True
        Exit For
    End If
Next

Dim sMsg As String = "=== K-Factor Validator ===" & vbCrLf & vbCrLf
sMsg &= "Material: " & sMaterial & vbCrLf
sMsg &= "Thickness: " & Math.Round(dThickness, 1) & " mm" & vbCrLf
sMsg &= "Current K-Factor: " & Math.Round(dKFactor, 3) & vbCrLf

If bFound Then
    sMsg &= "Expected range: " & dMin & " to " & dMax & vbCrLf & vbCrLf

    If dKFactor >= dMin And dKFactor <= dMax Then
        sMsg &= "✓ K-Factor is within expected range."
        MsgBox(sMsg, vbInformation, "K-Factor Validator")
    Else
        sMsg &= "✗ K-Factor is OUTSIDE expected range!" & vbCrLf
        sMsg &= "This may cause inaccurate flat patterns."
        MsgBox(sMsg, vbExclamation, "K-Factor Validator")
    End If
Else
    sMsg &= "No reference data for this material/thickness combination." & vbCrLf
    sMsg &= "Using default range: " & dMin & " to " & dMax
    MsgBox(sMsg, vbInformation, "K-Factor Validator")
End If
