'==============================================================================
' NAME:         Shrinkwrap Substitute Auto-Creator
' AUTHOR:       Jugoslav Ilic
' DATE:         04.09.2026.
' VERSION:      1.0.0
' LICENSE:      MIT — free to use with attribution
' GITHUB:       github.com/iddj27510/iLogic-Library
'
' DESCRIPTION:
'   Automatically creates a Shrinkwrap substitute for the selected assembly.
'   Configurable options: All solids, Simplified, Single solid.
'
' PARAMETERS:
'   None — configured at the top of the script.
'
' ASSUMPTIONS:
'   Active document must be an Assembly document.
'
' TESTED ON:
'   Autodesk Inventor 2027
'==============================================================================

' ============================================================
' CONFIGURATION — edit before use
' ============================================================
Dim sOutputFolder As String = ""
Dim sShrinkwrapType As String = "Simplified"   ' "AllSolids", "Simplified", "SingleSolid"
Dim sNamingSuffix As String = "_SW"
' ============================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument
Dim oAsmDef As AssemblyComponentDefinition = oAsmDoc.ComponentDefinition

' --- Set output folder ---
If sOutputFolder = "" Then
    sOutputFolder = System.IO.Path.GetDirectoryName(oAsmDoc.FullFileName)
End If

' --- Get part number for naming ---
Dim sPartNumber As String = ""
Try
    sPartNumber = oAsmDoc.PropertySets.Item("Design Tracking Properties").Item("Part Number").Value.ToString().Trim()
Catch
    sPartNumber = System.IO.Path.GetFileNameWithoutExtension(oAsmDoc.FullFileName)
End Try

Dim sOutputPath As String = sOutputFolder & "\" & sPartNumber & sNamingSuffix & ".ipt"

' --- Confirmation ---
Dim sMsg As String = "=== Shrinkwrap Substitute Auto-Creator ===" & vbCrLf & vbCrLf
sMsg &= "Assembly: " & System.IO.Path.GetFileName(oAsmDoc.FullFileName) & vbCrLf
sMsg &= "Type: " & sShrinkwrapType & vbCrLf
sMsg &= "Output: " & sOutputPath & vbCrLf
sMsg &= vbCrLf & "Proceed?"

If MsgBox(sMsg, vbYesNo + vbQuestion, "Shrinkwrap Creator") <> vbYes Then
    Exit Sub
End If

' --- Create Shrinkwrap ---
Try
    Dim oShrinkwrap As Shrinkwrap
    oShrinkwrap = oAsmDef.Shrinkwrap

    Dim oOptions As NameValueMap
    oOptions = ThisApplication.TransientObjects.CreateNameValueMap()

    Select Case sShrinkwrapType
        Case "AllSolids"
            oOptions.Add("IncludeAllSolids", True)
            oOptions.Add("IncludeSurfaceBodies", False)
            oOptions.Add("IncludeSketches", False)
            oOptions.Add("IncludeWorkFeatures", False)
            oOptions.Add("RemoveInternalVoids", True)
        Case "Simplified"
            oOptions.Add("IncludeAllSolids", True)
            oOptions.Add("IncludeSurfaceBodies", False)
            oOptions.Add("IncludeSketches", False)
            oOptions.Add("IncludeWorkFeatures", False)
            oOptions.Add("RemoveInternalVoids", True)
            oOptions.Add("SimplifyGeometry", True)
            oOptions.Add("MergeFaces", True)
        Case "SingleSolid"
            oOptions.Add("IncludeAllSolids", True)
            oOptions.Add("IncludeSurfaceBodies", False)
            oOptions.Add("IncludeSketches", False)
            oOptions.Add("IncludeWorkFeatures", False)
            oOptions.Add("RemoveInternalVoids", True)
            oOptions.Add("MergeFaces", True)
            oOptions.Add("SingleCompositeBody", True)
    End Select

    oShrinkwrap.CreateShrinkwrap(sOutputPath, oOptions)

    MsgBox("Shrinkwrap created successfully!" & vbCrLf & vbCrLf & "Output: " & sOutputPath, vbInformation, "Shrinkwrap Creator")

Catch ex As Exception
    MsgBox("Error creating shrinkwrap: " & ex.Message, vbExclamation, "Error")
End Try
