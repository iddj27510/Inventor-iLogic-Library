'==============================================================================
' NAME:         Parameter Cross-File Sync
' AUTHOR:       Jugoslav Ilic
' DATE:         04.09.2026.
' VERSION:      1.0.0
' LICENSE:      MIT — free to use with attribution
' GITHUB:       github.com/iddj27510/iLogic-Library
'
' DESCRIPTION:
'   Synchronizes parameters across multiple files.
'   Reads master list from a JSON file.
'
' PARAMETERS:
'   None — configured at the top of the script.
'
' ASSUMPTIONS:
'   Active document must be an Assembly document.
'
' TESTED ON:
'   Autodesk Inventor 2027
'==============================================================================

' ============================================================
' CONFIGURATION — edit before use
' ============================================================
Dim sJSONPath As String = ""
' ============================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument

' --- Find JSON file ---
If sJSONPath = "" Then
    sJSONPath = System.IO.Path.GetDirectoryName(oAsmDoc.FullFileName) & "\SyncParams.json"
End If

If Not System.IO.File.Exists(sJSONPath) Then
    MsgBox("Sync parameters file not found:" & vbCrLf & sJSONPath, vbExclamation, "File Not Found")
    Exit Sub
End If

' --- Read JSON ---
Dim sJSON As String = System.IO.File.ReadAllText(sJSONPath)
Dim oJSON As Object = Newtonsoft.Json.Linq.JObject.Parse(sJSON)

' --- Get list of parameters to sync ---
Dim aParams As New List(Of String)
For Each oItem As Object In oJSON("parameters")
    aParams.Add(oItem.ToString())
Next

' --- Sync parameters across open documents ---
Dim sLog As String = "=== Parameter Cross-File Sync ===" & vbCrLf & vbCrLf
Dim nSynced As Integer = 0

For Each oDoc As Document In ThisApplication.Documents
    Try
        If oDoc Is oAsmDoc Then Continue For

        Dim oParams As Parameters = oDoc.ComponentDefinition.Parameters

        For Each sParam As String In aParams
            Try
                Dim dValue As Double = oAsmDoc.ComponentDefinition.Parameters.Item(sParam).Value

                oParams.Item(sParam).Value = dValue
                nSynced = nSynced + 1
                sLog &= "✓ " & System.IO.Path.GetFileName(oDoc.FullFileName) & " - " & sParam & " = " & dValue & vbCrLf
            Catch
            End Try
        Next
    Catch
    End Try
Next

sLog &= vbCrLf & "Total parameters synced: " & nSynced

MsgBox(sLog, vbInformation, "Cross-File Sync")
