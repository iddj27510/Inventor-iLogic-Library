'==============================================================================
' NAME:         Suppressed Component Reporter
' AUTHOR:       Jugoslav Ilic
' DATE:         04.09.2026.
' VERSION:      1.0.0
' LICENSE:      MIT — free to use with attribution
' GITHUB:       github.com/iddj27510/iLogic-Library
'
' DESCRIPTION:
'   Lists all suppressed components in an assembly.
'   Exports to TXT or CSV.
'
' PARAMETERS:
'   None — configured at the top of the script.
'
' ASSUMPTIONS:
'   Active document must be an Assembly document.
'
' TESTED ON:
'   Autodesk Inventor 2027
'==============================================================================

' ============================================================
' CONFIGURATION — edit before use
' ============================================================
Dim bExportCSV As Boolean = True
' ============================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument

' --- Scan assembly ---
Dim sReport As String = "=== Suppressed Component Report ===" & vbCrLf & vbCrLf
Dim nSuppressed As Integer = 0

ScanSuppressed(oAsmDoc.ComponentDefinition.Occurrences, sReport, nSuppressed, 0)

If nSuppressed = 0 Then
    sReport &= "No suppressed components found."
Else
    sReport &= vbCrLf & "Total suppressed: " & nSuppressed
End If

' --- Export ---
If bExportCSV And nSuppressed > 0 Then
    Dim sCSVPath As String = System.IO.Path.GetDirectoryName(oAsmDoc.FullFileName) & _
                             "\Suppressed_Components_" & DateTime.Now.ToString("yyyyMMdd_HHmmss") & ".csv"

    Dim sCSV As String = "Level,Name,Part Number,Path" & vbCrLf
    sCSV &= sReport.Replace("  ", ",").Replace(" - ", ",")

    Try
        System.IO.File.WriteAllText(sCSVPath, sCSV)
        sReport &= vbCrLf & "Exported to: " & sCSVPath
    Catch
    End Try
End If

MsgBox(sReport, vbInformation, "Suppressed Component Report")

Sub ScanSuppressed(oOccs As ComponentOccurrences, ByRef sReport As String, ByRef nSuppressed As Integer, nLevel As Integer)
    Dim oOcc As ComponentOccurrence
    For Each oOcc In oOccs
        Try
            If oOcc.DefinitionDocumentType = DocumentTypeEnum.kVirtualComponentDocumentObject Then
                Continue For
            End If

            Dim sIndent As String = New String(" ", nLevel * 2)

            If oOcc.Suppressed Then
                nSuppressed = nSuppressed + 1

                Dim sPartNumber As String = ""
                Try
                    If oOcc.DefinitionDocumentType = DocumentTypeEnum.kPartDocumentObject Then
                        Dim oPart As PartDocument = oOcc.Definition.Document
                        sPartNumber = oPart.PropertySets.Item("Design Tracking Properties").Item("Part Number").Value.ToString()
                    End If
                Catch
                End Try

                sReport &= sIndent & "• " & oOcc.Name & " (Part Number: " & sPartNumber & ")" & vbCrLf
            End If

            If oOcc.DefinitionDocumentType = DocumentTypeEnum.kAssemblyDocumentObject Then
                Dim oSubAsm As AssemblyDocument = oOcc.Definition.Document
                ScanSuppressed(oSubAsm.ComponentDefinition.Occurrences, sReport, nSuppressed, nLevel + 1)
            End If
        Catch
        End Try
    Next
End Sub
