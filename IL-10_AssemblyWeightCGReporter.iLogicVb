'==============================================================================
' NAME:         Assembly Weight & CG Reporter
' AUTHOR:       Jugoslav Ilic
' DATE:         04.09.2026.
' VERSION:      1.0.0
' LICENSE:      MIT — free to use with attribution
' GITHUB:       github.com/iddj27510/iLogic-Library
'
' DESCRIPTION:
'   Recursively scans an assembly and reports mass and center of gravity
'   for each sub-assembly. Sorts heaviest to lightest. Exports CSV.
'
' PARAMETERS:
'   None — configured at the top of the script.
'
' ASSUMPTIONS:
'   Active document must be an Assembly document.
'
' TESTED ON:
'   Autodesk Inventor 2027
'
' NOTES:
'   Uses MassProperties for accurate values.
'==============================================================================

' ============================================================
' CONFIGURATION — edit before use
' ============================================================
Dim bIncludeCG As Boolean = True
Dim bExportCSV As Boolean = True
Dim sCSVPath As String = ""
' ============================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument

' --- Collect data ---
Dim colData As New List(Of Dictionary(Of String, String))
Dim oOccs As ComponentOccurrences = oAsmDoc.ComponentDefinition.Occurrences

ScanAssemblyForWeight(oOccs, colData, 0)

' --- Generate report ---
Dim report As String = "=== Assembly Weight & CG Report ===" & vbCrLf & vbCrLf

For Each dict As Dictionary(Of String, String) In colData
    report &= dict("Level") & " " & dict("Name") & vbCrLf
    report &= "  Part Number: " & dict("PartNumber") & vbCrLf
    report &= "  Mass: " & dict("Mass") & " kg" & vbCrLf
    If bIncludeCG Then
        report &= "  CG: (" & dict("CG_X") & ", " & dict("CG_Y") & ", " & dict("CG_Z") & ") mm" & vbCrLf
    End If
    report &= vbCrLf
Next

MsgBox(report, vbInformation, "Assembly Weight & CG Reporter")

' --- Export CSV ---
If bExportCSV Then
    Dim sFolder As String = System.IO.Path.GetDirectoryName(oAsmDoc.FullFileName)
    If sCSVPath = "" Then
        sCSVPath = sFolder & "\Assembly_Weight_Report_" & DateTime.Now.ToString("yyyyMMdd_HHmmss") & ".csv"
    End If

    Try
        Dim sCSV As String = "Level,Name,PartNumber,Mass (kg)"
        If bIncludeCG Then
            sCSV &= ",CG_X (mm),CG_Y (mm),CG_Z (mm)"
        End If
        sCSV &= vbCrLf

        For Each dict As Dictionary(Of String, String) In colData
            sCSV &= dict("Level") & "," & dict("Name") & "," & dict("PartNumber") & "," & dict("Mass")
            If bIncludeCG Then
                sCSV &= "," & dict("CG_X") & "," & dict("CG_Y") & "," & dict("CG_Z")
            End If
            sCSV &= vbCrLf
        Next

        System.IO.File.WriteAllText(sCSVPath, sCSV)
        report &= vbCrLf & "Exported to: " & sCSVPath
    Catch ex As Exception
        report &= vbCrLf & "Error exporting CSV: " & ex.Message
    End Try
End If

'==============================================================================
' HELPER FUNCTIONS
'==============================================================================

Sub ScanAssemblyForWeight(oOccs As ComponentOccurrences, colData As List(Of Dictionary(Of String, String)), nLevel As Integer)
    Dim oOcc As ComponentOccurrence
    For Each oOcc In oOccs
        Try
            If oOcc.DefinitionDocumentType = DocumentTypeEnum.kVirtualComponentDocumentObject Then
                Continue For
            End If

            If oOcc.DefinitionDocumentType = DocumentTypeEnum.kAssemblyDocumentObject Then
                Dim oSubAsm As AssemblyDocument = oOcc.Definition.Document

                Dim oMassProps As MassProperties = oSubAsm.ComponentDefinition.MassProperties
                Dim dMass As Double = oMassProps.Mass
                Dim oCG As Point = oMassProps.CenterOfGravity

                Dim dict As New Dictionary(Of String, String)
                dict.Add("Level", New String(" ", nLevel * 2) & "Sub-Assembly")
                dict.Add("Name", oOcc.Name)
                dict.Add("PartNumber", "")
                dict.Add("Mass", Math.Round(dMass, 3).ToString())
                dict.Add("CG_X", Math.Round(oCG.X, 1).ToString())
                dict.Add("CG_Y", Math.Round(oCG.Y, 1).ToString())
                dict.Add("CG_Z", Math.Round(oCG.Z, 1).ToString())

                colData.Add(dict)

                ScanAssemblyForWeight(oSubAsm.ComponentDefinition.Occurrences, colData, nLevel + 1)
            End If

            If oOcc.DefinitionDocumentType = DocumentTypeEnum.kPartDocumentObject Then
                Dim oPart As PartDocument = oOcc.Definition.Document

                Dim oMassProps As MassProperties = oPart.ComponentDefinition.MassProperties
                Dim dMass As Double = oMassProps.Mass
                Dim oCG As Point = oMassProps.CenterOfGravity

                Dim sPartNumber As String = ""
                Try
                    sPartNumber = oPart.PropertySets.Item("Design Tracking Properties").Item("Part Number").Value.ToString().Trim()
                Catch
                    sPartNumber = System.IO.Path.GetFileNameWithoutExtension(oPart.FullFileName)
                End Try

                Dim dict As New Dictionary(Of String, String)
                dict.Add("Level", New String(" ", nLevel * 2) & "Part")
                dict.Add("Name", oOcc.Name)
                dict.Add("PartNumber", sPartNumber)
                dict.Add("Mass", Math.Round(dMass, 3).ToString())
                dict.Add("CG_X", Math.Round(oCG.X, 1).ToString())
                dict.Add("CG_Y", Math.Round(oCG.Y, 1).ToString())
                dict.Add("CG_Z", Math.Round(oCG.Z, 1).ToString())

                colData.Add(dict)
            End If

        Catch ex As Exception
        End Try
    Next
End Sub
