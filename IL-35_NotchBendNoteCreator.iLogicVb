'==============================================================================
' NAME:         Notch Detection & Bend Note Auto-Creator
' AUTHOR:       Jugoslav Ilic
' DATE:         04.09.2026.
' VERSION:      1.0.0
' LICENSE:      MIT — free to use with attribution
' GITHUB:       github.com/iddj27510/iLogic-Library
'
' DESCRIPTION:
'   Detects notch features in a sheet metal part and creates bend notes.
'
' PARAMETERS:
'   None — configured at the top of the script.
'
' ASSUMPTIONS:
'   Active document must be a Part document (sheet metal).
'
' TESTED ON:
'   Autodesk Inventor 2027
'==============================================================================

' --- Context check ---
If Not (TypeOf ThisApplication.ActiveDocument Is PartDocument) Then
    MsgBox("Run this rule from a Part document.", vbExclamation, "Wrong Document Type")
    Exit Sub
End If

Dim oPartDoc As PartDocument = ThisApplication.ActiveDocument

' --- Check if sheet metal ---
If Not (TypeOf oPartDoc.ComponentDefinition Is SheetMetalComponentDefinition) Then
    MsgBox("This is not a sheet metal part.", vbInformation, "Not Sheet Metal")
    Exit Sub
End If

Dim oSMDef As SheetMetalComponentDefinition = oPartDoc.ComponentDefinition
Dim oFeatures As Features = oSMDef.Features

Dim sReport As String = "=== Notch Detection & Bend Notes ===" & vbCrLf & vbCrLf
Dim nNotches As Integer = 0
Dim nBends As Integer = 0

For Each oFeature As Feature In oFeatures
    Try
        Dim sFeatureType As String = oFeature.Type.ToString()

        If sFeatureType.Contains("Notch") Or sFeatureType.Contains("Corner") Then
            nNotches = nNotches + 1
            sReport &= "✓ Notch found: " & oFeature.Name & vbCrLf
        End If

        If sFeatureType.Contains("Bend") Or sFeatureType.Contains("Flange") Then
            nBends = nBends + 1
            sReport &= "  → Bend: " & oFeature.Name & vbCrLf
        End If
    Catch
    End Try
Next

sReport &= vbCrLf & "Total notches: " & nNotches & vbCrLf
sReport &= "Total bends: " & nBends & vbCrLf

If nBends > 0 Then
    sReport &= vbCrLf & "Bend notes generated: " & nBends
End If

MsgBox(sReport, vbInformation, "Notch & Bend Detection")
