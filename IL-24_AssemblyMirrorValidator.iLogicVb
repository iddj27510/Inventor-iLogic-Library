'==============================================================================
' NAME:         Assembly Mirror State Validator
' AUTHOR:       Jugoslav Ilic
' DATE:         04.09.2026.
' VERSION:      1.0.0
' LICENSE:      MIT — free to use with attribution
' GITHUB:       github.com/iddj27510/iLogic-Library
'
' DESCRIPTION:
'   Checks that mirrored components have consistent iProperties.
'   Suggests synchronization if they differ.
'
' PARAMETERS:
'   None — configured at the top of the script.
'
' ASSUMPTIONS:
'   Active document must be an Assembly document.
'
' TESTED ON:
'   Autodesk Inventor 2027
'==============================================================================

' ============================================================
' CONFIGURATION — edit before use
' ============================================================
Dim aPropertiesToCheck As New List(Of String) From {"Material", "Description", "Author"}
' ============================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument
Dim oOccs As ComponentOccurrences = oAsmDoc.ComponentDefinition.Occurrences

Dim sReport As String = "=== Assembly Mirror State Validator ===" & vbCrLf & vbCrLf
Dim nIssues As Integer = 0

Dim colMirrored As New List(Of String)
Dim colOriginals As New List(Of String)

For Each oOcc As ComponentOccurrence In oOccs
    Try
        If oOcc.DefinitionDocumentType = DocumentTypeEnum.kPartDocumentObject Then
            Dim oPart As PartDocument = oOcc.Definition.Document

            Dim bIsMirrored As Boolean = False
            Try
                If oOcc.Mirrored IsNot Nothing Then
                    bIsMirrored = True
                End If
            Catch
            End Try

            If bIsMirrored Then
                colMirrored.Add(oOcc.Name)
            Else
                colOriginals.Add(oOcc.Name)
            End If
        End If
    Catch
    End Try
Next

For Each sOriginal As String In colOriginals
    For Each sMirror As String In colMirrored
        If sOriginal = sMirror Then
            Dim oOccOriginal As ComponentOccurrence = oOccs.Item(sOriginal)
            Dim oOccMirror As ComponentOccurrence = oOccs.Item(sMirror)

            If oOccOriginal IsNot Nothing And oOccMirror IsNot Nothing Then
                If oOccOriginal.DefinitionDocumentType = DocumentTypeEnum.kPartDocumentObject And _
                   oOccMirror.DefinitionDocumentType = DocumentTypeEnum.kPartDocumentObject Then

                    Dim oPartOriginal As PartDocument = oOccOriginal.Definition.Document
                    Dim oPartMirror As PartDocument = oOccMirror.Definition.Document

                    Dim oPropsOriginal As PropertySet = oPartOriginal.PropertySets.Item("Design Tracking Properties")
                    Dim oPropsMirror As PropertySet = oPartMirror.PropertySets.Item("Design Tracking Properties")

                    For Each sProp As String In aPropertiesToCheck
                        Dim sValOriginal As String = ""
                        Dim sValMirror As String = ""

                        Try
                            sValOriginal = oPropsOriginal.Item(sProp).Value.ToString().Trim()
                        Catch
                        End Try

                        Try
                            sValMirror = oPropsMirror.Item(sProp).Value.ToString().Trim()
                        Catch
                        End Try

                        If sValOriginal <> sValMirror Then
                            sReport &= "⚠ " & sOriginal & " vs " & sMirror & ": " & sProp & " = " & sValOriginal & " vs " & sValMirror & vbCrLf
                            nIssues = nIssues + 1
                        End If
                    Next
                End If
            End If
        End If
    Next
Next

If nIssues = 0 Then
    sReport &= "✓ No issues found. All mirrored components are consistent."
Else
    sReport &= vbCrLf & "Found " & nIssues & " inconsistencies."
End If

MsgBox(sReport, vbInformation, "Mirror State Validator")
