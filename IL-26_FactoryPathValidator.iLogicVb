'==============================================================================
' NAME:         Factory Path Validator
' AUTHOR:       Jugoslav Ilic
' DATE:         04.09.2026.
' VERSION:      1.0.0
' LICENSE:      MIT — free to use with attribution
' GITHUB:       github.com/iddj27510/iLogic-Library
'
' DESCRIPTION:
'   Validates Factory Path iProperty against an approved list per project.
'   Detects empty fields and invalid values.
'
' PARAMETERS:
'   None — configured at the top of the script.
'
' ASSUMPTIONS:
'   Active document must be an Assembly document.
'
' TESTED ON:
'   Autodesk Inventor 2027
'
' NOTES:
'   Wyma Solutions experience: routing codes for 50+ countries.
'==============================================================================

' ============================================================
' CONFIGURATION — edit before use
' ============================================================
Dim sFactoryPathProperty As String = "Factory Path"
Dim sProjectCode As String = "PROJ-2024-EU"

Dim aValidPaths As New List(Of String) From {
    "EU-DE-01", "EU-NL-02", "EU-UK-03", "EU-FR-04",
    "US-TX-01", "US-CA-02", "NZ-AKL", "NZ-CHC"
}
' ============================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument

' --- Scan assembly ---
Dim errors As New List(Of String)
Dim warnings As New List(Of String)

ScanFactoryPath(oAsmDoc.ComponentDefinition.Occurrences, errors, warnings, 0)

' --- Generate report ---
Dim report As String = "=== Factory Path Validator ===" & vbCrLf & vbCrLf
report &= "Project: " & sProjectCode & vbCrLf
report &= "Valid paths: " & String.Join(", ", aValidPaths) & vbCrLf & vbCrLf

If errors.Count > 0 Then
    report &= "ERRORS (" & errors.Count & "):" & vbCrLf
    For Each s As String In errors
        report &= "  ! " & s & vbCrLf
    Next
Else
    report &= "No errors found." & vbCrLf
End If

If warnings.Count > 0 Then
    report &= vbCrLf & "WARNINGS (" & warnings.Count & "):" & vbCrLf
    For Each s As String In warnings
        report &= "  - " & s & vbCrLf
    Next
End If

MsgBox(report, vbInformation, "Factory Path Validator")

'==============================================================================
' HELPER FUNCTIONS
'==============================================================================

Sub ScanFactoryPath(oOccs As ComponentOccurrences, errors As List(Of String), warnings As List(Of String), nLevel As Integer)
    Dim oOcc As ComponentOccurrence
    For Each oOcc In oOccs
        Try
            If oOcc.DefinitionDocumentType = DocumentTypeEnum.kVirtualComponentDocumentObject Then
                Continue For
            End If

            If oOcc.DefinitionDocumentType = DocumentTypeEnum.kAssemblyDocumentObject Then
                Dim oSubAsm As AssemblyDocument = oOcc.Definition.Document
                ScanFactoryPath(oSubAsm.ComponentDefinition.Occurrences, errors, warnings, nLevel + 1)
                Continue For
            End If

            If oOcc.DefinitionDocumentType = DocumentTypeEnum.kPartDocumentObject Then
                Dim oPart As PartDocument = oOcc.Definition.Document
                Dim oProps As PropertySet = oPart.PropertySets.Item("Design Tracking Properties")

                Dim sPath As String = ""
                Try
                    sPath = oProps.Item(sFactoryPathProperty).Value.ToString().Trim()
                Catch
                End Try

                If sPath = "" Then
                    warnings.Add(oOcc.Name & " — Factory Path is empty")
                Else
                    Dim bValid As Boolean = False
                    For Each sValid As String In aValidPaths
                        If sPath = sValid Then
                            bValid = True
                            Exit For
                        End If
                    Next

                    If Not bValid Then
                        errors.Add(oOcc.Name & " — Invalid Factory Path: '" & sPath & "'")
                    End If
                End If
            End If

        Catch ex As Exception
            errors.Add(oOcc.Name & " — " & ex.Message)
        End Try
    Next
End Sub
