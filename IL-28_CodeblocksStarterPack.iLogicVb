'==============================================================================
' NAME:         Codeblocks Starter Template Pack
' AUTHOR:       Jugoslav Ilic
' DATE:         04.09.2026.
' VERSION:      1.0.0
' LICENSE:      MIT — free to use with attribution
' GITHUB:       github.com/iddj27510/iLogic-Library
'
' DESCRIPTION:
'   Collection of Codeblocks templates for Inventor 2027.
'   Each template is documented and ready for import.
'
' PARAMETERS:
'   None — used as reference.
'
' ASSUMPTIONS:
'   Inventor 2027 with Codeblocks support.
'
' TESTED ON:
'   Autodesk Inventor 2027
'
' NOTES:
'   This is a reference file with 5 Codeblocks templates.
'==============================================================================

' ============================================================
' TEMPLATE 1: Parameter Updater
' ============================================================
' Description: Reads value from form and updates model parameter
'
' Dim dLength As Double
' dLength = InputBox("Enter Length (mm):", "Parameter Updater", 100)
' If dLength > 0 Then
'     Parameters.Item("Length").Value = dLength
'     ThisApplication.ActiveDocument.Update()
' End If

' ============================================================
' TEMPLATE 2: iProperties Setter
' ============================================================
' Description: Sets iProperty from form
'
' Dim sValue As String
' sValue = InputBox("Enter Part Number:", "iProperties Setter", "")
' If sValue <> "" Then
'     iProperties.Value("Project", "Part Number") = sValue
' End If

' ============================================================
' TEMPLATE 3: Suppression Manager
' ============================================================
' Description: Toggles suppression of a component
'
' Dim oOcc As ComponentOccurrence
' For Each oOcc In Component.InventorComponent("ComponentName").Occurrences
'     oOcc.Suppressed = Not oOcc.Suppressed
' Next

' ============================================================
' TEMPLATE 4: Export Trigger
' ============================================================
' Description: Triggers PDF export from form
'
' Dim oDoc As Document = ThisApplication.ActiveDocument
' If TypeOf oDoc Is DrawingDocument Then
'     Dim oDraw As DrawingDocument = oDoc
'     Dim sPath As String = System.IO.Path.GetDirectoryName(oDoc.FullFileName)
'     Dim sPDFPath As String = sPath & "\" & System.IO.Path.GetFileNameWithoutExtension(oDoc.FullFileName) & ".pdf"
'     oDraw.ExportToPDF(sPDFPath)
'     MsgBox("PDF exported: " & sPDFPath, vbInformation, "Export Complete")
' End If

' ============================================================
' TEMPLATE 5: Validation Checker
' ============================================================
' Description: Checks condition and displays message
'
' Dim dLength As Double
' Try
'     dLength = Parameters.Item("Length").Value
' Catch
'     dLength = 0
' End Try
'
' If dLength < 100 Then
'     MsgBox("Warning: Length is less than 100 mm!", vbExclamation, "Validation")
' ElseIf dLength > 1000 Then
'     MsgBox("Warning: Length is greater than 1000 mm!", vbExclamation, "Validation")
' Else
'     MsgBox("Length is valid: " & dLength & " mm", vbInformation, "Validation")
' End If
