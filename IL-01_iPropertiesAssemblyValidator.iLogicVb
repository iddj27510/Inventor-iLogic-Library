'==============================================================================
' NAME:         iProperties Assembly Validator
' AUTHOR:       Jugoslav Ilic
' DATE:         04.09.2026.
' VERSION:      1.0.0
' LICENSE:      MIT — free to use with attribution
' GITHUB:       github.com/iddj27510/iLogic-Library
'
' DESCRIPTION:
'   Recursively scans an assembly and validates iProperties for each component.
'   Detects: empty Part Number, empty Description, missing Material,
'   inconsistent Author and Revision, empty Custom iProperties.
'
' PARAMETERS:
'   None — configured at the top of the script.
'
' ASSUMPTIONS:
'   Active document must be an Assembly document.
'
' TESTED ON:
'   Autodesk Inventor 2027
'
' NOTES:
'   Validates only — does not modify anything without explicit user click.
'   This rule is the manual version of the iProps Checker add-in.
'==============================================================================

' ============================================================
' CONFIGURATION — edit before use
' ============================================================
Dim bSkipCC As Boolean = True
Dim bSkipVirtual As Boolean = True
Dim bIncludeCustomProps As Boolean = True
Dim aCustomProps As New List(Of String) From {"Project", "Client", "Factory Path", "Drawing Number"}
Dim bShowWarnings As Boolean = True
' ============================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument

' --- Result lists ---
Dim errors As New List(Of String)
Dim warnings As New List(Of String)

' --- Run scan ---
ScanAssembly(oAsmDoc.ComponentDefinition.Occurrences, errors, warnings, 0)

' --- Generate report ---
Dim report As String = "=== iProperties Assembly Validator ===" & vbCrLf & vbCrLf

If errors.Count > 0 Then
    report &= "ERRORS (" & errors.Count & "):" & vbCrLf
    For Each s As String In errors
        report &= "  ! " & s & vbCrLf
    Next
Else
    report &= "No critical errors found." & vbCrLf
End If

If warnings.Count > 0 And bShowWarnings Then
    report &= vbCrLf & "WARNINGS (" & warnings.Count & "):" & vbCrLf
    For Each s As String In warnings
        report &= "  - " & s & vbCrLf
    Next
End If

report &= vbCrLf & "Total components scanned: " & (errors.Count + warnings.Count) & " issues found."

' --- Display report ---
MsgBox(report, vbInformation, "iProperties Assembly Validator")

' --- Optional: Export to file ---
Dim sFolder As String = System.IO.Path.GetDirectoryName(oAsmDoc.FullFileName)
Dim sLogFile As String = sFolder & "\iProperties_Validation_" & DateTime.Now.ToString("yyyyMMdd_HHmmss") & ".txt"
Try
    System.IO.File.WriteAllText(sLogFile, report)
Catch
End Try

'==============================================================================
' HELPER FUNCTIONS
'==============================================================================

Sub ScanAssembly(oOccs As ComponentOccurrences, errors As List(Of String), warnings As List(Of String), nLevel As Integer)
    Dim oOcc As ComponentOccurrence
    For Each oOcc In oOccs
        Try
            If oOcc.DefinitionDocumentType = DocumentTypeEnum.kVirtualComponentDocumentObject Then
                If bSkipVirtual Then Continue For
            End If

            Dim bIsCC As Boolean = False
            Try
                If oOcc.DefinitionDocumentType = DocumentTypeEnum.kPartDocumentObject Then
                    Dim oPart As PartDocument = oOcc.Definition.Document
                    If oPart.ComponentDefinition IsNot Nothing Then
                        Try
                            Dim oCC As Inventor.Property = oPart.PropertySets.Item("Design Tracking Properties").Item("Content Center Member")
                            If oCC IsNot Nothing Then bIsCC = True
                        Catch
                        End Try
                    End If
                End If
            Catch
            End Try

            If bIsCC And bSkipCC Then Continue For

            If oOcc.DefinitionDocumentType = DocumentTypeEnum.kAssemblyDocumentObject Then
                Dim oSubAsm As AssemblyDocument = oOcc.Definition.Document
                ScanAssembly(oSubAsm.ComponentDefinition.Occurrences, errors, warnings, nLevel + 1)
                Continue For
            End If

            If oOcc.DefinitionDocumentType = DocumentTypeEnum.kPartDocumentObject Then
                Dim oPart As PartDocument = oOcc.Definition.Document
                ValidatePart(oPart, oOcc, errors, warnings, nLevel)
            End If

        Catch ex As Exception
            errors.Add("Error scanning " & oOcc.Name & ": " & ex.Message)
        End Try
    Next
End Sub

Sub ValidatePart(oPart As PartDocument, oOcc As ComponentOccurrence, errors As List(Of String), warnings As List(Of String), nLevel As Integer)
    Try
        Dim sIndent As String = New String(" ", nLevel * 2)
        Dim sName As String = oOcc.Name

        Dim oProps As PropertySet = oPart.PropertySets.Item("Design Tracking Properties")

        Dim sPartNumber As String = ""
        Try
            sPartNumber = oProps.Item("Part Number").Value.ToString().Trim()
        Catch
        End Try

        If sPartNumber = "" Or sPartNumber = "Part1" Or sPartNumber = "Part" Then
            errors.Add(sIndent & sName & " — Part Number is empty or default")
        End If

        Dim sDesc As String = ""
        Try
            sDesc = oProps.Item("Description").Value.ToString().Trim()
        Catch
        End Try

        If sDesc = "" Then
            errors.Add(sIndent & sName & " — Description is empty")
        End If

        Dim sMat As String = ""
        Try
            sMat = oProps.Item("Material").Value.ToString().Trim()
        Catch
        End Try

        If sMat = "" Or sMat = "Generic" Then
            errors.Add(sIndent & sName & " — Material is empty or Generic")
        End If

        Dim sRev As String = ""
        Try
            sRev = oProps.Item("Revision Number").Value.ToString().Trim()
        Catch
        End Try

        If sRev = "" Then
            warnings.Add(sIndent & sName & " — Revision is empty")
        End If

        Dim sAuthor As String = ""
        Try
            sAuthor = oProps.Item("Author").Value.ToString().Trim()
        Catch
        End Try

        If sAuthor = "" Then
            warnings.Add(sIndent & sName & " — Author is empty")
        End If

        If bIncludeCustomProps Then
            For Each sProp As String In aCustomProps
                Dim sVal As String = ""
                Try
                    Dim oProp As Inventor.Property = oProps.Item(sProp)
                    sVal = oProp.Value.ToString().Trim()
                Catch
                End Try
                If sVal = "" Then
                    warnings.Add(sIndent & sName & " — Custom iProperty '" & sProp & "' is empty")
                End If
            Next
        End If

    Catch ex As Exception
        errors.Add(oOcc.Name & " — " & ex.Message)
    End Try
End Sub
