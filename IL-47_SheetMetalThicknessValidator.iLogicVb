'==============================================================================
' NAME:         Sheet Metal Thickness Group Validator
' AUTHOR:       Jugoslav Ilic
' DATE:         04.09.2026.
' VERSION:      1.0.0
' LICENSE:      MIT — free to use with attribution
' GITHUB:       github.com/iddj27510/iLogic-Library
'
' DESCRIPTION:
'   Groups sheet metal parts by material and checks thickness consistency.
'
' PARAMETERS:
'   None — configured at the top of the script.
'
' ASSUMPTIONS:
'   Active document must be an Assembly document.
'
' TESTED ON:
'   Autodesk Inventor 2027
'==============================================================================

' ============================================================
' CONFIGURATION — edit before use
' ============================================================
Dim dTolerance As Double = 0.1
' ============================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument

' --- Collect sheet metal data ---
Dim colData As New List(Of Dictionary(Of String, String))
Dim colErrors As New List(Of String)

ScanSheetMetal(oAsmDoc.ComponentDefinition.Occurrences, colData, colErrors, 0)

' --- Group by material ---
Dim dictGroups As New Dictionary(Of String, List(Of Dictionary(Of String, String)))

For Each dict As Dictionary(Of String, String) In colData
    Dim sMaterial As String = dict("Material")
    If Not dictGroups.ContainsKey(sMaterial) Then
        dictGroups.Add(sMaterial, New List(Of Dictionary(Of String, String)))
    End If
    dictGroups(sMaterial).Add(dict)
Next

' --- Check thickness consistency ---
Dim sReport As String = "=== Sheet Metal Thickness Group Validator ===" & vbCrLf & vbCrLf
Dim nIssues As Integer = 0

For Each sMaterial As String In dictGroups.Keys
    Dim colParts As List(Of Dictionary(Of String, String)) = dictGroups(sMaterial)
    Dim dFirstThickness As Double = 0
    Dim bFirst As Boolean = True

    sReport &= "Material: " & sMaterial & " (" & colParts.Count & " parts)" & vbCrLf

    For Each dict As Dictionary(Of String, String) In colParts
        Dim dThickness As Double = Double.Parse(dict("Thickness"))

        If bFirst Then
            dFirstThickness = dThickness
            bFirst = False
            sReport &= "  Reference thickness: " & dFirstThickness & " mm" & vbCrLf
        Else
            If Math.Abs(dThickness - dFirstThickness) > dTolerance Then
                sReport &= "  ✗ " & dict("Name") & ": " & dThickness & " mm (expected " & dFirstThickness & " mm)" & vbCrLf
                nIssues = nIssues + 1
            Else
                sReport &= "  ✓ " & dict("Name") & ": " & dThickness & " mm" & vbCrLf
            End If
        End If
    Next
    sReport &= vbCrLf
Next

If nIssues = 0 Then
    sReport &= "All sheet metal parts have consistent thickness per material group."
Else
    sReport &= "Found " & nIssues & " inconsistencies."
End If

MsgBox(sReport, vbInformation, "Sheet Metal Thickness Validator")

'==============================================================================
' HELPER FUNCTIONS
'==============================================================================

Sub ScanSheetMetal(oOccs As ComponentOccurrences, colData As List(Of Dictionary(Of String, String)), colErrors As List(Of String), nLevel As Integer)
    Dim oOcc As ComponentOccurrence
    For Each oOcc In oOccs
        Try
            If oOcc.DefinitionDocumentType = DocumentTypeEnum.kVirtualComponentDocumentObject Then
                Continue For
            End If

            If oOcc.DefinitionDocumentType = DocumentTypeEnum.kAssemblyDocumentObject Then
                Dim oSubAsm As AssemblyDocument = oOcc.Definition.Document
                ScanSheetMetal(oSubAsm.ComponentDefinition.Occurrences, colData, colErrors, nLevel + 1)
                Continue For
            End If

            If oOcc.DefinitionDocumentType = DocumentTypeEnum.kPartDocumentObject Then
                Dim oPart As PartDocument = oOcc.Definition.Document

                If TypeOf oPart.ComponentDefinition Is SheetMetalComponentDefinition Then
                    Dim oSMDef As SheetMetalComponentDefinition = oPart.ComponentDefinition

                    Dim sMaterial As String = ""
                    Dim dThickness As Double = oSMDef.Thickness

                    Try
                        sMaterial = oPart.PropertySets.Item("Design Tracking Properties").Item("Material").Value.ToString().Trim()
                    Catch
                        sMaterial = "Unknown"
                    End Try

                    Dim dict As New Dictionary(Of String, String)
                    dict.Add("Name", oOcc.Name)
                    dict.Add("Material", sMaterial)
                    dict.Add("Thickness", Math.Round(dThickness, 2).ToString())
                    dict.Add("Level", nLevel.ToString())

                    colData.Add(dict)
                End If
            End If
        Catch ex As Exception
            colErrors.Add(oOcc.Name & " — " & ex.Message)
        End Try
    Next
End Sub
