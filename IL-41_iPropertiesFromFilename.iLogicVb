'==============================================================================
' NAME:         iProperties from Filename Generator
' AUTHOR:       Jugoslav Ilic
' DATE:         04.09.2026.
' VERSION:      1.0.0
' LICENSE:      MIT — free to use with attribution
' GITHUB:       github.com/iddj27510/iLogic-Library
'
' DESCRIPTION:
'   Parses filename according to a defined regex pattern and populates iProperties.
'
' PARAMETERS:
'   None — configured at the top of the script.
'
' ASSUMPTIONS:
'   Active document must be a Part document.
'
' TESTED ON:
'   Autodesk Inventor 2027
'==============================================================================

' ============================================================
' CONFIGURATION — edit before use
' ============================================================
Dim sPattern As String = "^(\w+)-(\w+)-(.+)\.ipt$"
Dim bBatchMode As Boolean = False
' ============================================================

' --- Context check ---
Dim oDoc As Document = ThisApplication.ActiveDocument
If oDoc Is Nothing Then
    MsgBox("No active document.", vbExclamation, "Error")
    Exit Sub
End If

If Not (TypeOf oDoc Is PartDocument) Then
    MsgBox("Run this rule from a Part document.", vbExclamation, "Wrong Document Type")
    Exit Sub
End If

Dim oPartDoc As PartDocument = oDoc
Dim sFileName As String = System.IO.Path.GetFileNameWithoutExtension(oPartDoc.FullFileName)

' --- Parse filename ---
Dim oRegex As Object = CreateObject("VBScript.RegExp")
oRegex.Pattern = sPattern
oRegex.IgnoreCase = True

Dim oMatches As Object = oRegex.Execute(sFileName)

If oMatches.Count = 0 Then
    MsgBox("Filename does not match pattern: " & sFileName, vbExclamation, "No Match")
    Exit Sub
End If

Dim oMatch As Object = oMatches(0)
Dim sPartNumber As String = oMatch.SubMatches(0)
Dim sRevision As String = oMatch.SubMatches(1)
Dim sDescription As String = oMatch.SubMatches(2)

' --- Update iProperties ---
Try
    Dim oProps As PropertySet = oPartDoc.PropertySets.Item("Design Tracking Properties")

    Try
        oProps.Item("Part Number").Value = sPartNumber
    Catch
        oPartDoc.PropertySets.Item("Design Tracking Properties").Add(sPartNumber, "Part Number")
    End Try

    Try
        oProps.Item("Revision Number").Value = sRevision
    Catch
        oPartDoc.PropertySets.Item("Design Tracking Properties").Add(sRevision, "Revision Number")
    End Try

    Try
        oProps.Item("Description").Value = sDescription
    Catch
        oPartDoc.PropertySets.Item("Design Tracking Properties").Add(sDescription, "Description")
    End Try

    oPartDoc.Save()

    MsgBox("iProperties updated from filename:" & vbCrLf & vbCrLf & _
           "Part Number: " & sPartNumber & vbCrLf & _
           "Revision: " & sRevision & vbCrLf & _
           "Description: " & sDescription, vbInformation, "Filename Parser")

Catch ex As Exception
    MsgBox("Error: " & ex.Message, vbExclamation, "Error")
End Try
