'==============================================================================
' NAME:         Revision Auto-Incrementor
' AUTHOR:       Jugoslav Ilic
' DATE:         04.09.2026.
' VERSION:      1.0.0
' LICENSE:      MIT — free to use with attribution
' GITHUB:       github.com/iddj27510/iLogic-Library
'
' DESCRIPTION:
'   Automatically increments the Revision iProperty according to a defined scheme.
'   Records previous revision and date of change.
'
' PARAMETERS:
'   None — configured at the top of the script.
'
' ASSUMPTIONS:
'   Active document must have a Revision iProperty.
'
' TESTED ON:
'   Autodesk Inventor 2027
'
' NOTES:
'   Nothing changes without explicit user confirmation.
'==============================================================================

' ============================================================
' CONFIGURATION — edit before use
' ============================================================
Dim sScheme As String = "Letters"   ' "Letters", "Numbers", or "Custom"
Dim sCustomPattern As String = ""
Dim bUpdateDrawings As Boolean = False
Dim bAddToLog As Boolean = True
' ============================================================

' --- Context check ---
Dim oDoc As Document = ThisApplication.ActiveDocument
If oDoc Is Nothing Then
    MsgBox("No active document.", vbExclamation, "Error")
    Exit Sub
End If

' --- Get current revision ---
Dim oProps As PropertySet = oDoc.PropertySets.Item("Design Tracking Properties")
Dim sCurrentRev As String = ""
Try
    sCurrentRev = oProps.Item("Revision Number").Value.ToString().Trim()
Catch
    sCurrentRev = "A"
End Try

' --- Calculate new revision ---
Dim sNewRev As String = IncrementRevision(sCurrentRev, sScheme, sCustomPattern)

If sNewRev = sCurrentRev Then
    MsgBox("Could not increment revision. Check the scheme configuration.", vbExclamation, "Error")
    Exit Sub
End If

' --- Show preview and ask for confirmation ---
Dim sMsg As String = "Current Revision: " & sCurrentRev & vbCrLf
sMsg &= "New Revision: " & sNewRev & vbCrLf & vbCrLf
sMsg &= "This will update the Revision iProperty."

If bUpdateDrawings Then
    sMsg &= vbCrLf & "Referenced drawings will also be updated."
End If

sMsg &= vbCrLf & vbCrLf & "Proceed?"

Dim nResponse As Integer = MsgBox(sMsg, vbYesNo + vbQuestion, "Revision Auto-Incrementor")
If nResponse <> vbYes Then
    Exit Sub
End If

' --- Apply the change ---
Try
    Try
        Dim oBackupProp As Inventor.Property = oDoc.PropertySets.Item("Design Tracking Properties").Item("Previous Revision")
        oBackupProp.Value = sCurrentRev
    Catch
        Try
            oDoc.PropertySets.Item("Design Tracking Properties").Add(sCurrentRev, "Previous Revision")
        Catch
        End Try
    End Try

    oProps.Item("Revision Number").Value = sNewRev

    Try
        oProps.Item("Revision Date").Value = DateTime.Now.ToString("dd.MM.yyyy")
    Catch
        Try
            oDoc.PropertySets.Item("Design Tracking Properties").Add(DateTime.Now.ToString("dd.MM.yyyy"), "Revision Date")
        Catch
        End Try
    End Try

    oDoc.Save()

    If bUpdateDrawings Then
        UpdateReferencedDrawings(oDoc, sCurrentRev, sNewRev)
    End If

    If bAddToLog Then
        AddToReleaseLog(oDoc, sCurrentRev, sNewRev)
    End If

    MsgBox("Revision updated from " & sCurrentRev & " to " & sNewRev & ".", vbInformation, "Done")

Catch ex As Exception
    MsgBox("Error updating revision: " & ex.Message, vbExclamation, "Error")
End Try

'==============================================================================
' HELPER FUNCTIONS
'==============================================================================

Function IncrementRevision(sCurrent As String, sScheme As String, sPattern As String) As String
    Select Case sScheme
        Case "Letters"
            Return IncrementLetters(sCurrent)
        Case "Numbers"
            Return IncrementNumbers(sCurrent)
        Case "Custom"
            If sPattern <> "" Then
                Return IncrementCustom(sCurrent, sPattern)
            End If
    End Select
    Return sCurrent
End Function

Function IncrementLetters(sCurrent As String) As String
    sCurrent = sCurrent.ToUpper()
    If Not System.Text.RegularExpressions.Regex.IsMatch(sCurrent, "^[A-Z]+$") Then
        Return sCurrent
    End If

    Dim chars() As Char = sCurrent.ToCharArray()
    Dim i As Integer = chars.Length - 1

    While i >= 0
        If chars(i) < "Z"c Then
            chars(i) = Chr(Asc(chars(i)) + 1)
            Return New String(chars)
        Else
            chars(i) = "A"c
            i -= 1
        End If
    End While

    Return "A" & New String(chars)
End Function

Function IncrementNumbers(sCurrent As String) As String
    Dim nValue As Integer
    If Integer.TryParse(sCurrent, nValue) Then
        nValue += 1
        Return nValue.ToString("D" & sCurrent.Length)
    End If
    Return sCurrent
End Function

Function IncrementCustom(sCurrent As String, sPattern As String) As String
    Return sCurrent
End Function

Sub UpdateReferencedDrawings(oDoc As Document, sOldRev As String, sNewRev As String)
    Dim oApp As Application = ThisApplication
    Dim oDoc As Document

    For Each oDoc In oApp.Documents
        If TypeOf oDoc Is DrawingDocument Then
            Dim oDraw As DrawingDocument = oDoc
            Try
                For Each oRef As Document In oDraw.ReferencedDocuments
                    If oRef.FullFileName = oDoc.FullFileName Then
                        Try
                            Dim oProps As PropertySet = oDraw.PropertySets.Item("Design Tracking Properties")
                            oProps.Item("Revision Number").Value = sNewRev
                            oDraw.Save()
                        Catch
                        End Try
                    End If
                Next
            Catch
            End Try
        End If
    Next
End Sub

Sub AddToReleaseLog(oDoc As Document, sOldRev As String, sNewRev As String)
    Dim sLogPath As String = System.IO.Path.GetDirectoryName(oDoc.FullFileName) & "\Release_Log.txt"
    Dim sEntry As String = DateTime.Now.ToString("yyyy-MM-dd HH:mm:ss") & " | " & _
                           System.IO.Path.GetFileName(oDoc.FullFileName) & " | " & _
                           sOldRev & " → " & sNewRev & " | " & _
                           ThisApplication.UserName

    Try
        System.IO.File.AppendAllText(sLogPath, sEntry & vbCrLf)
    Catch
    End Try
End Sub
