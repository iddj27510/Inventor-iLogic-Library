'==============================================================================
' NAME:         Design Review Checklist Generator
' AUTHOR:       Jugoslav Ilic
' DATE:         04.09.2026.
' VERSION:      1.0.0
' LICENSE:      MIT — free to use with attribution
' GITHUB:       github.com/iddj27510/iLogic-Library
'
' DESCRIPTION:
'   Generates a design review checklist directly from Inventor.
'   HTML report with BOM and checklist.
'
' PARAMETERS:
'   None — configured at the top of the script.
'
' ASSUMPTIONS:
'   Active document must be an Assembly document.
'
' TESTED ON:
'   Autodesk Inventor 2027
'==============================================================================

' --- Context check ---
If Not (TypeOf ThisApplication.ActiveDocument Is AssemblyDocument) Then
    MsgBox("Run this rule from an Assembly document.", vbExclamation, "Wrong Document Type")
    Exit Sub
End If

Dim oAsmDoc As AssemblyDocument = ThisApplication.ActiveDocument

' --- Get iProperties ---
Dim sPartNumber As String = ""
Dim sDescription As String = ""
Dim sAuthor As String = ""
Dim sRevision As String = ""

Try
    Dim oProps As PropertySet = oAsmDoc.PropertySets.Item("Design Tracking Properties")
    sPartNumber = oProps.Item("Part Number").Value.ToString()
    sDescription = oProps.Item("Description").Value.ToString()
    sAuthor = oProps.Item("Author").Value.ToString()
    sRevision = oProps.Item("Revision Number").Value.ToString()
Catch
End Try

' --- Get mass properties ---
Dim dMass As Double = 0
Try
    dMass = oAsmDoc.ComponentDefinition.MassProperties.Mass
Catch
End Try

' --- Get BOM count ---
Dim nComponents As Integer = 0
Try
    Dim oOccs As ComponentOccurrences = oAsmDoc.ComponentDefinition.Occurrences
    For Each oOcc As ComponentOccurrence In oOccs
        nComponents = nComponents + 1
    Next
Catch
End Try

' --- Generate HTML ---
Dim sHTML As String = "<html><head><title>Design Review Checklist</title>"
sHTML &= "<style>body{font-family:Arial;margin:40px}table{border-collapse:collapse;width:100%}"
sHTML &= "th,td{border:1px solid #ddd;padding:8px;text-align:left}"
sHTML &= "th{background-color:#4CAF50;color:white}"
sHTML &= ".header{background-color:#f2f2f2;padding:20px;border-radius:5px}"
sHTML &= "</style></head><body>"

' Header
sHTML &= "<div class='header'>"
sHTML &= "<h1>Design Review Checklist</h1>"
sHTML &= "<p><b>Part Number:</b> " & sPartNumber & "</p>"
sHTML &= "<p><b>Description:</b> " & sDescription & "</p>"
sHTML &= "<p><b>Author:</b> " & sAuthor & "</p>"
sHTML &= "<p><b>Revision:</b> " & sRevision & "</p>"
sHTML &= "<p><b>Date:</b> " & DateTime.Now.ToString("dd.MM.yyyy") & "</p>"
sHTML &= "</div>"

' Summary
sHTML &= "<h2>Summary</h2>"
sHTML &= "<table>"
sHTML &= "<tr><th>Metric</th><th>Value</th></tr>"
sHTML &= "<tr><td>Total Components</td><td>" & nComponents & "</td></tr>"
sHTML &= "<tr><td>Total Mass (kg)</td><td>" & Math.Round(dMass, 2) & "</td></tr>"
sHTML &= "</table>"

' Checklist
sHTML &= "<h2>Checklist</h2>"
sHTML &= "<table>"
sHTML &= "<tr><th>#</th><th>Item</th><th>Status</th><th>Comments</th></tr>"
sHTML &= "<tr><td>1</td><td>All iProperties populated</td><td>☐</td><td></td></tr>"
sHTML &= "<tr><td>2</td><td>BOM complete</td><td>☐</td><td></td></tr>"
sHTML &= "<tr><td>3</td><td>Drawings updated</td><td>☐</td><td></td></tr>"
sHTML &= "<tr><td>4</td><td>Reviews complete</td><td>☐</td><td></td></tr>"
sHTML &= "<tr><td>5</td><td>Approved for release</td><td>☐</td><td></td></tr>"
sHTML &= "</table>"

sHTML &= "<p><i>Generated by Design Review Checklist Generator</i></p>"
sHTML &= "</body></html>"

' --- Save HTML ---
Dim sOutputPath As String = System.IO.Path.GetDirectoryName(oAsmDoc.FullFileName) & _
                            "\DesignReview_" & DateTime.Now.ToString("yyyyMMdd_HHmmss") & ".html"

Try
    System.IO.File.WriteAllText(sOutputPath, sHTML)
    MsgBox("Design Review Checklist generated:" & vbCrLf & sOutputPath, vbInformation, "Checklist Generated")
Catch ex As Exception
    MsgBox("Error: " & ex.Message, vbExclamation, "Error")
End Try
